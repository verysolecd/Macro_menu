Sub CATMain()
Set rootPrd = CATIA.ActiveDocument.Product
Set Asm = rootPrd.GetItem("BillOfMaterial")
Dim Ary(7) 
Ary(0) = "Number"
Ary(1) = "Part Number"
Ary(2) = "Quantity"
Ary(3) = "Nomenclature"
Ary(4) = "Defintion"
Ary(5) = "Mass"
Ary(6) = "Density"
Ary(7) = "Material"
Asm.SetCurrentFormat Ary

Dim ary2(1)
ary2(0) = "Number"
ary2(1) = "Part Number"
Asm.SetSecondaryFormat ary2

Asm.Print "TXT", "D:\bill.TXT", rootPrd

End Sub
