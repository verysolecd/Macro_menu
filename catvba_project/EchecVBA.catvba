Attribute VB_Name = "FenetreJeuDeEchec"
Attribute VB_Base = "0{B4A1BE6D-E16A-41E3-8BF7-B65933D92CE1}{205D1654-D806-4AF0-AFC6-21866902C4FA}"
Attribute VB_GlobalNameSpace = False
Attribute VB_Creatable = False
Attribute VB_PredeclaredId = True
Attribute VB_Exposed = False
Attribute VB_TemplateDerived = False
Attribute VB_Customizable = False
Private Sub Pos00_Click()           'Pour chaque bouton on appele la fonction ActionButton
    Call ActionButton(0, 0, Pos00)
End Sub
Private Sub Pos01_Click()
    Call ActionButton(0, 1, Pos01)
End Sub
Private Sub Pos02_Click()
    Call ActionButton(0, 2, Pos02)
End Sub
Private Sub Pos03_Click()
    Call ActionButton(0, 3, Pos03)
End Sub
Private Sub Pos04_Click()
    Call ActionButton(0, 4, Pos04)
End Sub
Private Sub Pos05_Click()
    Call ActionButton(0, 5, Pos05)
End Sub
Private Sub Pos06_Click()
    Call ActionButton(0, 6, Pos06)
End Sub
Private Sub Pos07_Click()
    Call ActionButton(0, 7, Pos07)
End Sub
Private Sub Pos10_Click()
    Call ActionButton(1, 0, Pos10)
End Sub
Private Sub Pos11_Click()
    Call ActionButton(1, 1, Pos11)
End Sub
Private Sub Pos12_Click()
    Call ActionButton(1, 2, Pos12)
End Sub
Private Sub Pos13_Click()
    Call ActionButton(1, 3, Pos13)
End Sub
Private Sub Pos14_Click()
    Call ActionButton(1, 4, Pos14)
End Sub
Private Sub Pos15_Click()
    Call ActionButton(1, 5, Pos15)
End Sub
Private Sub Pos16_Click()
    Call ActionButton(1, 6, Pos16)
End Sub
Private Sub Pos17_Click()
    Call ActionButton(1, 7, Pos17)
End Sub
Private Sub Pos20_Click()
    Call ActionButton(2, 0, Pos20)
End Sub
Private Sub Pos21_Click()
    Call ActionButton(2, 1, Pos21)
End Sub
Private Sub Pos22_Click()
    Call ActionButton(2, 2, Pos22)
End Sub
Private Sub Pos23_Click()
    Call ActionButton(2, 3, Pos23)
End Sub
Private Sub Pos24_Click()
    Call ActionButton(2, 4, Pos24)
End Sub
Private Sub Pos25_Click()
    Call ActionButton(2, 5, Pos25)
End Sub
Private Sub Pos26_Click()
    Call ActionButton(2, 6, Pos26)
End Sub
Private Sub Pos27_Click()
    Call ActionButton(2, 7, Pos27)
End Sub
Private Sub Pos30_Click()
    Call ActionButton(3, 0, Pos30)
End Sub
Private Sub Pos31_Click()
    Call ActionButton(3, 1, Pos31)
End Sub
Private Sub Pos32_Click()
    Call ActionButton(3, 2, Pos32)
End Sub
Private Sub Pos33_Click()
    Call ActionButton(3, 3, Pos33)
End Sub
Private Sub Pos34_Click()
    Call ActionButton(3, 4, Pos34)
End Sub
Private Sub Pos35_Click()
    Call ActionButton(3, 5, Pos35)
End Sub
Private Sub Pos36_Click()
    Call ActionButton(3, 6, Pos36)
End Sub
Private Sub Pos37_Click()
    Call ActionButton(3, 7, Pos37)
End Sub
Private Sub Pos40_Click()
    Call ActionButton(4, 0, Pos40)
End Sub
Private Sub Pos41_Click()
    Call ActionButton(4, 1, Pos41)
End Sub
Private Sub Pos42_Click()
    Call ActionButton(4, 2, Pos42)
End Sub
Private Sub Pos43_Click()
    Call ActionButton(4, 3, Pos43)
End Sub
Private Sub Pos44_Click()
    Call ActionButton(4, 4, Pos44)
End Sub
Private Sub Pos45_Click()
    Call ActionButton(4, 5, Pos45)
End Sub
Private Sub Pos46_Click()
    Call ActionButton(4, 6, Pos46)
End Sub
Private Sub Pos47_Click()
    Call ActionButton(4, 7, Pos47)
End Sub
Private Sub Pos50_Click()
    Call ActionButton(5, 0, Pos50)
End Sub
Private Sub Pos51_Click()
    Call ActionButton(5, 1, Pos51)
End Sub
Private Sub Pos52_Click()
    Call ActionButton(5, 2, Pos52)
End Sub
Private Sub Pos53_Click()
    Call ActionButton(5, 3, Pos53)
End Sub
Private Sub Pos54_Click()
    Call ActionButton(5, 4, Pos54)
End Sub
Private Sub Pos55_Click()
    Call ActionButton(5, 5, Pos55)
End Sub
Private Sub Pos56_Click()
    Call ActionButton(5, 6, Pos56)
End Sub
Private Sub Pos57_Click()
    Call ActionButton(5, 7, Pos57)
End Sub
Private Sub Pos60_Click()
    Call ActionButton(6, 0, Pos60)
End Sub
Private Sub Pos61_Click()
    Call ActionButton(6, 1, Pos61)
End Sub
Private Sub Pos62_Click()
    Call ActionButton(6, 2, Pos62)
End Sub
Private Sub Pos63_Click()
    Call ActionButton(6, 3, Pos63)
End Sub
Private Sub Pos64_Click()
    Call ActionButton(6, 4, Pos64)
End Sub
Private Sub Pos65_Click()
    Call ActionButton(6, 5, Pos65)
End Sub
Private Sub Pos66_Click()
    Call ActionButton(6, 6, Pos66)
End Sub
Private Sub Pos67_Click()
    Call ActionButton(6, 7, Pos67)
End Sub
Private Sub Pos70_Click()
    Call ActionButton(7, 0, Pos70)
End Sub
Private Sub Pos71_Click()
    Call ActionButton(7, 1, Pos71)
End Sub
Private Sub Pos72_Click()
    Call ActionButton(7, 2, Pos72)
End Sub
Private Sub Pos73_Click()
    Call ActionButton(7, 3, Pos73)
End Sub
Private Sub Pos74_Click()
    Call ActionButton(7, 4, Pos74)
End Sub
Private Sub Pos75_Click()
    Call ActionButton(7, 5, Pos75)
End Sub
Private Sub Pos76_Click()
    Call ActionButton(7, 6, Pos76)
End Sub
Private Sub Pos77_Click()
    Call ActionButton(7, 7, Pos77)
End Sub

Public Sub Colorer()                        'On met tout l'échiquier aux couleurs initiales
    Pos00.BackColor = &H808080
    Pos01.BackColor = RGB(255, 255, 255)
    Pos02.BackColor = &H808080
    Pos03.BackColor = RGB(255, 255, 255)
    Pos04.BackColor = &H808080
    Pos05.BackColor = RGB(255, 255, 255)
    Pos06.BackColor = &H808080
    Pos07.BackColor = RGB(255, 255, 255)
    
    Pos10.BackColor = RGB(255, 255, 255)
    Pos11.BackColor = &H808080
    Pos12.BackColor = RGB(255, 255, 255)
    Pos13.BackColor = &H808080
    Pos14.BackColor = RGB(255, 255, 255)
    Pos15.BackColor = &H808080
    Pos16.BackColor = RGB(255, 255, 255)
    Pos17.BackColor = &H808080
    
    Pos20.BackColor = &H808080
    Pos21.BackColor = RGB(255, 255, 255)
    Pos22.BackColor = &H808080
    Pos23.BackColor = RGB(255, 255, 255)
    Pos24.BackColor = &H808080
    Pos25.BackColor = RGB(255, 255, 255)
    Pos26.BackColor = &H808080
    Pos27.BackColor = RGB(255, 255, 255)
    
    Pos30.BackColor = RGB(255, 255, 255)
    Pos31.BackColor = &H808080
    Pos32.BackColor = RGB(255, 255, 255)
    Pos33.BackColor = &H808080
    Pos34.BackColor = RGB(255, 255, 255)
    Pos35.BackColor = &H808080
    Pos36.BackColor = RGB(255, 255, 255)
    Pos37.BackColor = &H808080
    
    Pos40.BackColor = &H808080
    Pos41.BackColor = RGB(255, 255, 255)
    Pos42.BackColor = &H808080
    Pos43.BackColor = RGB(255, 255, 255)
    Pos44.BackColor = &H808080
    Pos45.BackColor = RGB(255, 255, 255)
    Pos46.BackColor = &H808080
    Pos47.BackColor = RGB(255, 255, 255)
    
    Pos50.BackColor = RGB(255, 255, 255)
    Pos51.BackColor = &H808080
    Pos52.BackColor = RGB(255, 255, 255)
    Pos53.BackColor = &H808080
    Pos54.BackColor = RGB(255, 255, 255)
    Pos55.BackColor = &H808080
    Pos56.BackColor = RGB(255, 255, 255)
    Pos57.BackColor = &H808080
    
    Pos60.BackColor = &H808080
    Pos61.BackColor = RGB(255, 255, 255)
    Pos62.BackColor = &H808080
    Pos63.BackColor = RGB(255, 255, 255)
    Pos64.BackColor = &H808080
    Pos65.BackColor = RGB(255, 255, 255)
    Pos66.BackColor = &H808080
    Pos67.BackColor = RGB(255, 255, 255)
    
    Pos70.BackColor = RGB(255, 255, 255)
    Pos71.BackColor = &H808080
    Pos72.BackColor = RGB(255, 255, 255)
    Pos73.BackColor = &H808080
    Pos74.BackColor = RGB(255, 255, 255)
    Pos75.BackColor = &H808080
    Pos76.BackColor = RGB(255, 255, 255)
    Pos77.BackColor = &H808080
    
End Sub

Public Sub ActionButton(ByVal posX, ByVal posY, ByRef Button)
    'Fonction appelé quand un bouton est cliqué
    If selection = True Then                    'Si une case a déjà été selectionnéé
        Call Deplacer(posX, posY)               'On appelle la fonction deplacer
        Call Colorer                            'On colore tout les cases
        Call ChangeFigure(Button, posX, posY)   'On met à jour les figures dans l'échiquier 2D
        Exit Sub                                'On sort de la fonction
    End If
    
    If selection = False Then                   'Pour selectioner la pièce à bouger
        posInitialeX = posX                     'On recupère la position initiale X
        posInitialeY = posY                     'On recupère la position initiale Y
        selection = True                        'On change pour entrer dans l'autre cas la prochaine fois
        Button.BackColor = RGB(0, 255, 0)       'On change la couleur de la case selectionnée à verte
        Exit Sub                                'On sort de la fonction
    End If
    
End Sub

Public Sub ChangeFigure(ByRef Button, ByVal posFinaleX, ByVal posFinaleY)
    'Fonction utilisé pour mettre à jour les figures dans l'échiquier 2D
    If mouvementPermis = True Then                  'Si le mouvement est permis,
        If posInitialeX = 0 Then                    'on enlève la figure du bouton
            If posInitialeY = 0 Then                'où était la pièce
                Pos00.Picture = LoadPicture(none)   'Tout ces lignes servent
            ElseIf posInitialeY = 1 Then            'servent à vérifier dans quel case
                Pos01.Picture = LoadPicture(none)   'était la pièce
            ElseIf posInitialeY = 2 Then
                Pos02.Picture = LoadPicture(none)
            ElseIf posInitialeY = 3 Then
                Pos03.Picture = LoadPicture(none)
            ElseIf posInitialeY = 4 Then
                Pos04.Picture = LoadPicture(none)
            ElseIf posInitialeY = 5 Then
                Pos05.Picture = LoadPicture(none)
            ElseIf posInitialeY = 6 Then
                Pos06.Picture = LoadPicture(none)
            ElseIf posInitialeY = 7 Then
                Pos07.Picture = LoadPicture(none)
            End If
        
        ElseIf posInitialeX = 1 Then
            If posInitialeY = 0 Then
                Pos10.Picture = LoadPicture(none)
            ElseIf posInitialeY = 1 Then
                Pos11.Picture = LoadPicture(none)
            ElseIf posInitialeY = 2 Then
                Pos12.Picture = LoadPicture(none)
            ElseIf posInitialeY = 3 Then
                Pos13.Picture = LoadPicture(none)
            ElseIf posInitialeY = 4 Then
                Pos14.Picture = LoadPicture(none)
            ElseIf posInitialeY = 5 Then
                Pos15.Picture = LoadPicture(none)
            ElseIf posInitialeY = 6 Then
                Pos16.Picture = LoadPicture(none)
            ElseIf posInitialeY = 7 Then
                Pos17.Picture = LoadPicture(none)
            End If
        
        ElseIf posInitialeX = 2 Then
            If posInitialeY = 0 Then
                Pos20.Picture = LoadPicture(none)
            ElseIf posInitialeY = 1 Then
                Pos21.Picture = LoadPicture(none)
            ElseIf posInitialeY = 2 Then
                Pos22.Picture = LoadPicture(none)
            ElseIf posInitialeY = 3 Then
                Pos23.Picture = LoadPicture(none)
            ElseIf posInitialeY = 4 Then
                Pos24.Picture = LoadPicture(none)
            ElseIf posInitialeY = 5 Then
                Pos25.Picture = LoadPicture(none)
            ElseIf posInitialeY = 6 Then
                Pos26.Picture = LoadPicture(none)
            ElseIf posInitialeY = 7 Then
                Pos27.Picture = LoadPicture(none)
            End If
            
        ElseIf posInitialeX = 3 Then
            If posInitialeY = 0 Then
                Pos30.Picture = LoadPicture(none)
            ElseIf posInitialeY = 1 Then
                Pos31.Picture = LoadPicture(none)
            ElseIf posInitialeY = 2 Then
                Pos32.Picture = LoadPicture(none)
            ElseIf posInitialeY = 3 Then
                Pos33.Picture = LoadPicture(none)
            ElseIf posInitialeY = 4 Then
                Pos34.Picture = LoadPicture(none)
            ElseIf posInitialeY = 5 Then
                Pos35.Picture = LoadPicture(none)
            ElseIf posInitialeY = 6 Then
                Pos36.Picture = LoadPicture(none)
            ElseIf posInitialeY = 7 Then
                Pos37.Picture = LoadPicture(none)
            End If
            
        ElseIf posInitialeX = 4 Then
            If posInitialeY = 0 Then
                Pos40.Picture = LoadPicture(none)
            ElseIf posInitialeY = 1 Then
                Pos41.Picture = LoadPicture(none)
            ElseIf posInitialeY = 2 Then
                Pos42.Picture = LoadPicture(none)
            ElseIf posInitialeY = 3 Then
                Pos43.Picture = LoadPicture(none)
            ElseIf posInitialeY = 4 Then
                Pos44.Picture = LoadPicture(none)
            ElseIf posInitialeY = 5 Then
                Pos45.Picture = LoadPicture(none)
            ElseIf posInitialeY = 6 Then
                Pos46.Picture = LoadPicture(none)
            ElseIf posInitialeY = 7 Then
                Pos47.Picture = LoadPicture(none)
            End If
            
        ElseIf posInitialeX = 5 Then
            If posInitialeY = 0 Then
                Pos50.Picture = LoadPicture(none)
            ElseIf posInitialeY = 1 Then
                Pos51.Picture = LoadPicture(none)
            ElseIf posInitialeY = 2 Then
                Pos52.Picture = LoadPicture(none)
            ElseIf posInitialeY = 3 Then
                Pos53.Picture = LoadPicture(none)
            ElseIf posInitialeY = 4 Then
                Pos54.Picture = LoadPicture(none)
            ElseIf posInitialeY = 5 Then
                Pos55.Picture = LoadPicture(none)
            ElseIf posInitialeY = 6 Then
                Pos56.Picture = LoadPicture(none)
            ElseIf posInitialeY = 7 Then
                Pos57.Picture = LoadPicture(none)
            End If
        
        ElseIf posInitialeX = 6 Then
            If posInitialeY = 0 Then
                Pos60.Picture = LoadPicture(none)
            ElseIf posInitialeY = 1 Then
                Pos61.Picture = LoadPicture(none)
            ElseIf posInitialeY = 2 Then
                Pos62.Picture = LoadPicture(none)
            ElseIf posInitialeY = 3 Then
                Pos63.Picture = LoadPicture(none)
            ElseIf posInitialeY = 4 Then
                Pos64.Picture = LoadPicture(none)
            ElseIf posInitialeY = 5 Then
                Pos65.Picture = LoadPicture(none)
            ElseIf posInitialeY = 6 Then
                Pos66.Picture = LoadPicture(none)
            ElseIf posInitialeY = 7 Then
                Pos67.Picture = LoadPicture(none)
            End If
        
        ElseIf posInitialeX = 7 Then
            If posInitialeY = 0 Then
                Pos70.Picture = LoadPicture(none)
            ElseIf posInitialeY = 1 Then
                Pos71.Picture = LoadPicture(none)
            ElseIf posInitialeY = 2 Then
                Pos72.Picture = LoadPicture(none)
            ElseIf posInitialeY = 3 Then
                Pos73.Picture = LoadPicture(none)
            ElseIf posInitialeY = 4 Then
                Pos74.Picture = LoadPicture(none)
            ElseIf posInitialeY = 5 Then
                Pos75.Picture = LoadPicture(none)
            ElseIf posInitialeY = 6 Then
                Pos76.Picture = LoadPicture(none)
            ElseIf posInitialeY = 7 Then
                Pos77.Picture = LoadPicture(none)
            End If
        End If
    End If
    
    Dim playerInd As Integer                        'On crée un indice pour les joueurs pour les noms des figures
    changeLabelName (tourPlayer)                    'On change le nom affiché pour montré à qui est le tour
    
    For i = 0 To 31                                                         'On regarde quelle est la pièce
        If posFinaleX = CorpsPosX(i) And posFinaleY = CorpsPosY(i) Then     'qui se trouve maintenant sur la case finale
            If CorpsPlayer(i) = playerName1 Then                            'Si elle appartient au premier joueur
                playerInd = 1                                               'alors indice = 1
            Else                                                            'sinon
                playerInd = 2                                               'indice = 2
            End If
            'On change la figure affiché selon le type de la pièce et le joueur (donc la couleur de la pièce) ex: roi1, pion2...
            Button.Picture = LoadPicture(chemin & "\" & CorpsType(i) & playerInd & ".bmp")
        End If
    Next i
    mouvementPermis = False     'On remet la variable à False pour recomencer le processus
End Sub

Public Sub changeLabelName(ByVal nom As String)     'On appele cette fonction pour changer le nom affiché du tour
    playerLabel.Caption = nom                       'On change la valeur du label
    playerLabel.TextAlign = fmTextAlignCenter       'On aligne le nom
    If nom = playerName1 Then                       'Si c'est le premier joueur
        visionObs.Viewpoint3D = viewpoint3D1        'On change la vue pour la camera 1
    Else                                            'Sinon
        visionObs.Viewpoint3D = viewpoint3D2        'On change la vue pour la camera 2
    End If
End Sub

Attribute VB_Name = "JeuDeEchec"
Sub Deplacer(ByVal posFinaleX, ByVal posFinaleY)
    'Fonction pour deplacer les pièces dans l'échiquier
    valeurXInit = (posInitialeX * -2) - 1       'On calcul les valeurs des contraintes
    valeurYInit = (posInitialeY * -2) - 1       'basé sur les positions de l'échiquier
    valeurXFin = (posFinaleX * -2) - 1
    valeurYFin = (posFinaleY * -2) - 1

    Set doc = CATIA.ActiveDocument.Product      'On charge le document CATIA active
    
    For i = 0 To 31                             'Pour toutes les pièces
        If CorpsPosX(i) = posInitialeX And CorpsPosY(i) = posInitialeY And CorpsPlayer(i) = tourPlayer Then 'S'il y a une pièce dans la position intiale
            Call mouvementVerif(i, posFinaleX, posFinaleY)                                                  'On vérifie si le mouvement est possible
            If mouvementPermis = True Then                                                                  'Si c'est possible
                For j = 0 To 31                                                                             'On regarde les autres pièces
                    If i = j Then                                                                           'Si c'est la même pièce on fait rien
                    Else
                        If CorpsPosX(j) = posFinaleX And CorpsPosY(j) = posFinaleY Then                     'On cherche une pièce dans la position finale
                            If CorpsPlayer(i) = CorpsPlayer(j) Then                                         'Si la pièce appartient au même joueur
                                MsgBox "Case déjà occupée", vbOKOnly, Attention                             'Alors on dit que la case est occuppée
                                mouvementPermis = False                                                     'Le mouvement n'est donc pas permis
                                selection = False                                                           'On deselectionne la case
                                Exit Sub                                                                    'On sort de la fonction
                            Else
                                For T = 0 To tempsAnimation                                                 'Sinon on commence l'animation pour enlever la pièce adversaire
                                doc.Connections("CATIAConstraints").Item("Decalage" & j & "Z").Dimension.Value = 3 * T / tempsAnimation 'On monte selon Z
                                doc.Update                                                                  'On met à jour la visualisation
                                DoEvents                                                                    'pour créer une animation
                                Next T                                                                      'en utilisant des iterations
                                
                                If CorpsPlayer(j) = playerName1 Then                                        'On fait la même chose pour les autres directions
                                    For T = 0 To tempsAnimation                                             'Et les autres pièces concernées
                                    doc.Connections("CATIAConstraints").Item("Decalage" & j & "X").Dimension.Value = Dehors1 * T / tempsAnimation + (tempsAnimation - T) * valeurXFin / tempsAnimation
                                    doc.Connections("CATIAConstraints").Item("Decalage" & j & "Y").Dimension.Value = 2 * T / tempsAnimation + (tempsAnimation - T) * valeurYFin / tempsAnimation
                                    doc.Update
                                    DoEvents
                                    Next T
                                    Dehors1 = Dehors1 - 2                                                   'Pour que les pièces qui sortent ne se superposent pas
                                    If CorpsType(j) = "roi" Then                                            'Si la pièce éliminée est un roi
                                        MsgBox "Le joueur " & playerName2 & " a gagné", vbInformation, "Fin de la partie"   'Fin de partie
                                        FenetreJeuDeEchec.Hide                                              'On ferme la fenêtre
                                    End If
                                Else
                                    For T = 0 To tempsAnimation                                             'Semblable mais pour l'autre joueur
                                    doc.Connections("CATIAConstraints").Item("Decalage" & j & "X").Dimension.Value = Dehors2 * T / tempsAnimation + (tempsAnimation - T) * valeurXFin / tempsAnimation
                                    doc.Connections("CATIAConstraints").Item("Decalage" & j & "Y").Dimension.Value = -17 * T / tempsAnimation + (tempsAnimation - T) * valeurYFin / tempsAnimation
                                    doc.Update                                                              'la différence est que cette pièce va
                                    DoEvents                                                                'de l'autre côté
                                    Next T
                                    Dehors2 = Dehors2 - 2
                                    If CorpsType(j) = "roi" Then
                                        MsgBox "Le joueur " & playerName1 & " a gagné", vbInformation, "Fin de la partie"
                                        FenetreJeuDeEchec.Hide
                                    End If
                                End If
                                
                                For T = 0 To tempsAnimation                                                 'On descend la pièce
                                doc.Connections("CATIAConstraints").Item("Decalage" & j & "Z").Dimension.Value = (tempsAnimation - T) * 3 / tempsAnimation + -1 * T / tempsAnimation
                                doc.Update
                                DoEvents
                                Next T
                                
                                CorpsPosX(j) = 20   'On met une valeur seulement pour ne pas déranger les mouvements futurs
                                CorpsPosY(j) = 0
                            End If
                        End If
                    End If
                Next j
                    For T = 0 To tempsAnimation     'On fait l'animation pour la pièce i selon Z
                        doc.Connections("CATIAConstraints").Item("Decalage" & i & "Z").Dimension.Value = 3 * T / tempsAnimation
                        doc.Update
                        DoEvents
                    Next T
                
                    For T = 0 To tempsAnimation     'On fait l'animation pour la pièce i selon X et Y
                        doc.Connections("CATIAConstraints").Item("Decalage" & i & "X").Dimension.Value = valeurXFin * T / tempsAnimation + (tempsAnimation - T) * valeurXInit / tempsAnimation
                        doc.Connections("CATIAConstraints").Item("Decalage" & i & "Y").Dimension.Value = valeurYFin * T / tempsAnimation + (tempsAnimation - T) * valeurYInit / tempsAnimation
                        doc.Update
                        DoEvents
                    Next T
                    
                    For T = 0 To tempsAnimation     'On fait l'animation pour la pièce i selon Z
                        doc.Connections("CATIAConstraints").Item("Decalage" & i & "Z").Dimension.Value = (tempsAnimation - T) * 3 / tempsAnimation
                        doc.Update
                        DoEvents
                    Next T
                If tourPlayer = playerName1 Then    'On change le tour
                    tourPlayer = playerName2
                Else
                    tourPlayer = playerName1
                End If
                CorpsPosX(i) = posFinaleX           'La pièce possède desormais la position finale
                CorpsPosY(i) = posFinaleY
                PionPremierMouvement(i) = True      'Elle a réalisé certainement la premier mouvement
                selection = False                   'On deselectionne les cases
                doc.Update                          'On met à jour la fenêtre CATIA
                Exit Sub                            'On sort de la fonction
            Else
                MsgBox "Mouvement non permis"       'Si le mouvement n'est pas permis
            End If
            selection = False                       'On deselectionne les cases
            doc.Update                              'On met à jour
            Exit Sub                                'On sort de la fonction
        End If
    Next i
    selection = False                               'Si rien se passe alors on deselectionne les cases
    doc.Update                                      'On met à jour

End Sub


Sub mouvementVerif(ByVal i, ByVal posFinaleX, ByVal posFinaleY)
    'Fonction pour analyser si le mouvement est permis compte tenu de la direction et des autres pièces
    'If ------- -> analyse si le mouvement est permis étant donnée seulement la position initiale et finale
        'For ----- -> analyse pour toutes les pièces s'il y a une entre la position finale et intiale
            'S'il y en a, alors on peut pas bouger
        'Prochaine pièce
    'Fin du if
    
    '------------------------------- Pion joueur 1 ----------------------------
    If CorpsType(i) = "pion" And CorpsPlayer(i) = playerName1 And (Abs(posFinaleY - posInitialeY) < 2 And (posFinaleX - posInitialeX) = 1) Then
        If Abs(posFinaleY - posInitialeY) = 1 Then
            For j = 16 To 31
                If CorpsPosX(j) = posFinaleX And posFinaleY = CorpsPosY(j) Then
                    mouvementPermis = True
                End If
            Next j
        Else
            mouvementPermis = True
        End If
        
    '------------------------------- Pion joueur 2 -----------------------------
    ElseIf CorpsType(i) = "pion" And CorpsPlayer(i) = playerName2 And (Abs(posFinaleY - posInitialeY) < 2 And (posFinaleX - posInitialeX) = -1) Then
        If Abs(posFinaleY - posInitialeY) = 1 Then
            For j = 0 To 15
                If CorpsPosX(j) = posFinaleX And posFinaleY = CorpsPosY(j) Then
                    mouvementPermis = True
                End If
            Next j
        Else
            mouvementPermis = True
        End If
        
    '---------------------- Pion joueur 1 premier mouvement ----------------------
    ElseIf CorpsType(i) = "pion" And CorpsPlayer(i) = playerName1 And posFinaleY = posInitialeY And (posFinaleX - posInitialeX) = 2 And PionPremierMouvement(i) = False Then
        mouvementPermis = True
        PionPremierMouvement(i) = True
        
    '---------------------- Pion joueur 2 premier mouvement ----------------------
    ElseIf CorpsType(i) = "pion" And CorpsPlayer(i) = playerName2 And posFinaleY = posInitialeY And (posFinaleX - posInitialeX) = -2 And PionPremierMouvement(i) = False Then
        mouvementPermis = True
        PionPremierMouvement(i) = True
        
    '----------------------------------- Roi -------------------------------------
    ElseIf CorpsType(i) = "roi" And (Abs(posFinaleX - posInitialeX) <= 1 And Abs(posFinaleY - posInitialeY) <= 1) Then
        mouvementPermis = True
    ElseIf CorpsType(i) = "fou" And (Abs(posFinaleX - posInitialeX) = Abs(posFinaleY - posInitialeY)) And Abs(posInitialeX - posFinaleX) > 0 Then
        For k = 1 To Abs(posFinaleX - posInitialeX) - 1
            For j = 0 To 31
                If CorpsPosX(j) = posInitialeX + k * Sgn(posFinaleX - posInitialeX) And CorpsPosY(j) = posInitialeY + k * Sgn(posFinaleY - posInitialeY) Then
                    mouvementPermis = False
                    Exit Sub
                End If
            Next j
        Next k
        mouvementPermis = True
        
    '---------------------------------- Cheval -----------------------------------
    ElseIf CorpsType(i) = "cheval" And ((Abs(posFinaleX - posInitialeX) = 2 And Abs(posFinaleY - posInitialeY) = 1) Or (Abs(posFinaleX - posInitialeX) = 1 And Abs(posFinaleY - posInitialeY) = 2)) Then
        mouvementPermis = True
    
    '----------------------------------- Fou -------------------------------------
    ElseIf CorpsType(i) = "tour" And ((posFinaleX = posInitialeX) Or (posFinaleY = posInitialeY)) Then
        For k = 1 To Abs(posFinaleX - posInitialeX + posFinaleY - posInitialeY) - 1
            For j = 0 To 31
                If CorpsPosX(j) = posInitialeX + k * Sgn(posFinaleX - posInitialeX) And CorpsPosY(j) = posInitialeY + k * Sgn(posFinaleY - posInitialeY) Then
                    mouvementPermis = False
                    Exit Sub
                End If
            Next j
        Next k
        mouvementPermis = True
        
    '------------------------------------ Reine ------------------------------------
    ElseIf CorpsType(i) = "reine" And ((Abs(posFinaleX - posInitialeX) = Abs(posFinaleY - posInitialeY)) Or ((posFinaleX = posInitialeX) Or (posFinaleY = posInitialeY))) Then
        If Abs(posFinaleX - posInitialeX) = Abs(posFinaleY - posInitialeY) Then ' Fou
            For k = 1 To Abs(posFinaleX - posInitialeX) - 1
                For j = 0 To 31
                    If CorpsPosX(j) = posInitialeX + k * Sgn(posFinaleX - posInitialeX) And CorpsPosY(j) = posInitialeY + k * Sgn(posFinaleY - posInitialeY) Then
                        mouvementPermis = False
                        Exit Sub
                    End If
                Next j
            Next k
        ElseIf posFinaleX = posInitialeX Or posFinaleY = posInitialeY Then ' Tour
            For k = 1 To Abs(posFinaleX - posInitialeX + posFinaleY - posInitialeY) - 1
                For j = 0 To 31
                    If CorpsPosX(j) = posInitialeX + k * Sgn(posFinaleX - posInitialeX) And CorpsPosY(j) = posInitialeY + k * Sgn(posFinaleY - posInitialeY) Then
                        mouvementPermis = False
                        Exit Sub
                    End If
                Next j
            Next k
        End If
        mouvementPermis = True
        
    '--------------------------- Si aucun des cas s'applique  ----------------------
    Else
        mouvementPermis = False
    End If
    
End Sub

Sub CATMain()

playerName1 = InputBox("Mettez le nom du joueur 1", "Nom du joueur 1")  'On prend les noms des joueurs
playerName2 = InputBox("Mettez le nom du joueur 2", "Nom du joueur 2")
If playerName1 = "" Then                                                'Si on ne met rien
    playerName1 = "Player 1"                                            'Alors nom = Player 1
End If
If playerName2 = "" Or playerName2 = playerName1 Then                   'la même chose
    playerName2 = "Player 2"
End If

For i = 0 To 31                     'On initialise avec premier mouvement pas réalisé
    PionPremierMouvement(i) = False
Next i

' -------- 1er joueur -------

For i = 0 To 7                      'Pions du premier joueur
    CorpsPosX(i) = 1
    CorpsPosY(i) = i
    CorpsPlayer(i) = playerName1
    CorpsType(i) = "pion"
Next i

CorpsPosX(8) = 0                    'On défini que le corps d'indice 8 occupe
CorpsPosY(8) = 0                    'la case de position (0,0) de l'échiquier
CorpsPlayer(8) = playerName1        'Cette pièce appartient au joueur 1
CorpsType(8) = "tour"               'C'est une tour

CorpsPosX(9) = 0                    'Les autres pièces suivent la même logique
CorpsPosY(9) = 1
CorpsPlayer(9) = playerName1
CorpsType(9) = "cheval"

CorpsPosX(10) = 0
CorpsPosY(10) = 2
CorpsPlayer(10) = playerName1
CorpsType(10) = "fou"

CorpsPosX(11) = 0
CorpsPosY(11) = 3
CorpsPlayer(11) = playerName1
CorpsType(11) = "roi"

CorpsPosX(12) = 0
CorpsPosY(12) = 4
CorpsPlayer(12) = playerName1
CorpsType(12) = "reine"

CorpsPosX(13) = 0
CorpsPosY(13) = 5
CorpsPlayer(13) = playerName1
CorpsType(13) = "fou"

CorpsPosX(14) = 0
CorpsPosY(14) = 6
CorpsPlayer(14) = playerName1
CorpsType(14) = "cheval"

CorpsPosX(15) = 0
CorpsPosY(15) = 7
CorpsPlayer(15) = playerName1
CorpsType(15) = "tour"

' -------- 2eme joueur -------

For i = 16 To 23                    'Pions du deuxieme joueur
    CorpsPosX(i) = 6
    CorpsPosY(i) = i - 16
    CorpsPlayer(i) = playerName2
    CorpsType(i) = "pion"
Next i

CorpsPosX(24) = 7
CorpsPosY(24) = 0
CorpsPlayer(24) = playerName2
CorpsType(24) = "tour"

CorpsPosX(25) = 7
CorpsPosY(25) = 1
CorpsPlayer(25) = playerName2
CorpsType(25) = "cheval"

CorpsPosX(26) = 7
CorpsPosY(26) = 2
CorpsPlayer(26) = playerName2
CorpsType(26) = "fou"

CorpsPosX(27) = 7
CorpsPosY(27) = 3
CorpsPlayer(27) = playerName2
CorpsType(27) = "roi"

CorpsPosX(28) = 7
CorpsPosY(28) = 4
CorpsPlayer(28) = playerName2
CorpsType(28) = "reine"

CorpsPosX(29) = 7
CorpsPosY(29) = 5
CorpsPlayer(29) = playerName2
CorpsType(29) = "fou"

CorpsPosX(30) = 7
CorpsPosY(30) = 6
CorpsPlayer(30) = playerName2
CorpsType(30) = "cheval"

CorpsPosX(31) = 7
CorpsPosY(31) = 7
CorpsPlayer(31) = playerName2
CorpsType(31) = "tour"

' --- Parametres ---

selection = False               'Aucune case n'est sélectionnée
mouvementPermis = False         'initialisation de variable
tourPlayer = playerName1        'Le premier joueur commence
tempsAnimation = 3              'On défini la quantité d'iterations
Dehors1 = 0                     'On initialise les variables
Dehors2 = 0

Dim productDocumentPrincipal As ProductDocument         'Charger le document
Set productDocumentPrincipal = CATIA.ActiveDocument     'CATIA en cours
Dim JeuDeEchec As Product                               'Define le produit
Set JeuDeEchec = productDocumentPrincipal.Product       'en cours
Dim deplacements As Constraints                         'On charge les contraintes
Set deplacements = JeuDeEchec.Connections("CATIAConstraints")
chemin = productDocumentPrincipal.Path

Dim deplacementX(31) As Constraint                      'On crée des listes de contraintes
Dim deplacementY(31) As Constraint                      'mais pas encore associées au produit
Dim deplacementZ(31) As Constraint
Dim XValeur(31) As Length                               'On crée des listes de valeurs
Dim YValeur(31) As Length                               'mais pas encore associées au produit
Dim ZValeur(31) As Length

For i = 0 To 31
    Set deplacementX(i) = deplacements.Item("Decalage" & i & "X")   'On associe les contraintes
    Set deplacementY(i) = deplacements.Item("Decalage" & i & "Y")   'aux éléments des listes
    Set deplacementZ(i) = deplacements.Item("Decalage" & i & "Z")
    Set XValeur(i) = deplacementX(i).Dimension
    Set YValeur(i) = deplacementY(i).Dimension
    Set ZValeur(i) = deplacementZ(i).Dimension
    deplacementZ(i).Orientation = catCstOrientOpposite              'Orientation pour la dimension Z
    XValeur(i).Value = (CorpsPosX(i) * -2) - 1                      'On associe les valeurs
    YValeur(i).Value = (CorpsPosY(i) * -2) - 1                      'selon les paramètres définis
    ZValeur(i).Value = 0                                            'au préalable
Next i

'------ Configurations pour l'angle d'affichage ----------

Set fenetrePrincipale = CATIA.ActiveWindow      'On charge la fênetre principale
Set visionObs = fenetrePrincipale.ActiveViewer  'On le define comme observateur

Set camera3D1 = visionObs.NewCamera()           'On crée 2 nouvelles cameras
Set camera3D2 = visionObs.NewCamera()

Set viewpoint3D1 = camera3D1.Viewpoint3D        'On crée le viewpoint des cameras
Set viewpoint3D2 = camera3D2.Viewpoint3D

'--- Paramètres de la camera 1 ---

origineCamera3D1(0) = -8.973027                 'On défini les paramètres de la camera 1
origineCamera3D1(1) = -16.130461
origineCamera3D1(2) = 15.830488
Set viewpoint3D1Variant = viewpoint3D1
viewpoint3D1Variant.PutOrigin origineCamera3D1  'Origine de la camera

directionVision3D1(0) = 0.509698
directionVision3D1(1) = 0.744311
directionVision3D1(2) = -0.43152
Set viewpoint3D1Variant = viewpoint3D1
viewpoint3D1Variant.PutSightDirection directionVision3D1    'Vision de la camera

directionUp3D1(0) = 0.250634
directionUp3D1(1) = 0.351352
directionUp3D1(2) = 0.902072
Set viewpoint3D1Variant = viewpoint3D1
viewpoint3D1Variant.PutUpDirection directionUp3D1

viewpoint3D1.FocusDistance = 30.75342            'Focus
viewpoint3D1.Zoom = 0.135442                     'Zoom de la camera

'--- Paramètres de la camera 2 ---

origineCamera3D2(0) = 25.86628                   'Semblable à la camera 1
origineCamera3D2(1) = 27.935162
origineCamera3D2(2) = 15.100451
Set viewpoint3D2Variant = viewpoint3D2
viewpoint3D2Variant.PutOrigin origineCamera3D2

directionVision3D2(0) = -0.604699
directionVision3D2(1) = -0.663898
directionVision3D2(2) = -0.440093
Set viewpoint3D2Variant = viewpoint3D2
viewpoint3D2Variant.PutSightDirection directionVision3D2

directionUp3D2(0) = -0.258623
directionUp3D2(1) = -0.361786
directionUp3D2(2) = 0.890391
Set viewpoint3D2Variant = viewpoint3D2
viewpoint3D2Variant.PutUpDirection directionUp3D2

viewpoint3D2.FocusDistance = 30.774475
viewpoint3D2.Zoom = 0.136432

' -----------------

visionObs.Viewpoint3D = viewpoint3D1                'On defini la camera 1 pour commencer la partie
Call FenetreJeuDeEchec.changeLabelName(playerName1) 'On change le label pour le premier nom
JeuDeEchec.Update                                   'On met à jour la fenêtre CATIA
FenetreJeuDeEchec.Show                              'On affiche la fenêtre 2D pour jouer

Dim camerasCrees As Cameras                         'À la fin, on recupère les cameras
Set camerasCrees = productDocumentPrincipal.Cameras 'Pour les effacer

camerasCrees.Remove "camera000"                     'On efface les cameras créées
camerasCrees.Remove "camera001"

End Sub

Attribute VB_Name = "Variables"
'----------- Variables pour le mouvement -------------------------

Public posInitialeX As Integer      'Position X sélectionnée
Public posInitialeY As Integer      'Position Y sélectionnée
Public valeurXFin As Double         'Position X finale
Public valeurYFin As Double         'Position Y finale
Public tempsAnimation As Integer    'Combien d'iterations pour l'animation
Public selection As Boolean         'Variable de sélection
Public mouvementPermis As Boolean   'Variable pour savoir si le mouvement est permis ou pas
Public tourPlayer As String         'Pour changer les tours

'--------- Variables pour la définition des pièces ---------------

Public CorpsPlayer(31) As String    'A quelle joueur la pièce appartienne
Public CorpsPosX(31) As Integer     'Position X de la pièce
Public CorpsPosY(31) As Integer     'Position Y de la pièce
Public CorpsPosZ(31) As Integer     'Position Z de la pièce pour l'animation
Public CorpsType(31) As String      'Le type de la pièce
Public PionPremierMouvement(31) As Boolean  'Premier mouvement du pion
Public Dehors1 As Integer           'Position quand la pièce est enlévée
Public Dehors2 As Integer           'Aussi mais pour l'autre joueur
Public playerName1 As String        'Nom du premier joueur
Public playerName2 As String        'Nom du déuxième joueur
Public chemin As String             'Pour récupérer l'adresse des fichiers

'----- Pour acceder a la camera depuis tout les fonctions -----

Public fenetrePrincipale As SpecsAndGeomWindow     'On crée la variable pour la fênetre principale
Public visionObs As Viewer3D                       'On crée la variable pour un observateur
Public camera3D1 As Camera3D                       'On crée la variable pour la première camera
Public camera3D2 As Camera3D                       'On crée la variable pour la deuxième camera
Public viewpoint3D1 As Viewpoint3D                 'Variable pour le viewpoint de la camera 1
Public viewpoint3D2 As Viewpoint3D                 'Variable pour le viewpoint de la camera 2

'--- Paramètres de la camera 1 ---
Public origineCamera3D1(2)             'Position de l'origine de la camera
Public directionVision3D1(2)           'Angle de vision
Public directionUp3D1(2)

'--- Paramètres de la camera 2 ---
Public origineCamera3D2(2)              'Semblable à la camera 1
Public directionVision3D2(2)
Public directionUp3D2(2)
