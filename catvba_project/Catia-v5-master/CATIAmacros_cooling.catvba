Attribute VB_Name = "getItemInfo"

'**********************************************************************************************************
'This macro gives the object name and type.

'Instructions for use:
'Select one or more objects and run macro.
'Macro will count number of items in selection and return name and type for each object.
'**********************************************************************************************************
'Created by Per Björk, Engineering partner 2014

'variables
Dim errorMes As Variant
Dim oSel As Selection

Sub CATMain()
On Error GoTo errorHandler  'errorhandlng
    
        Set oSel = Catia.ActiveDocument.Selection
            If oSel.Count = 0 Then
                MsgBox "Nothing selected!" & vbNewLine & "Select an object."        'give errormessage if selection is empty
            End If
            
        MsgBox ("Number of objects selected: " & oSel.Count)    'list number of objects selected
            For i = 1 To oSel.Count     'go through selection of objects
                Set selEl = oSel.Item(i)
                    MsgBox ("Item name: " & selEl.Value.Name & vbNewLine & "Item type: " & selEl.Type)  'list name and type
            Next
                oSel.Clear      'clear selection
            
            
errorHandler:   'error messages
    If Err.Number = -2147467259 Then
        errorMes = MsgBox("No active CATIA document!" & vbNewLine & "Load a CATIA document and select at least one object.", vbCritical, "Error!")
            Err.Number = 0
    End If
    
End Sub

Attribute VB_Name = "mainForm"
Attribute VB_Base = "0{16AC5CF5-222E-45C9-B8F4-C8B00BF4E6A4}{3FC270DE-BFD1-494A-8D17-1519F48A389D}"
Attribute VB_GlobalNameSpace = False
Attribute VB_Creatable = False
Attribute VB_PredeclaredId = True
Attribute VB_Exposed = False
Attribute VB_TemplateDerived = False
Attribute VB_Customizable = False
'Created by Per Björk, Engineering Partner 2014

Private Sub MultiPage1_Change()

End Sub

Private Sub UserForm_Initialize()   'do this when form opens
    Dim objName As String
        Dim winName As String
            Dim winCount As Integer         'count windows and display the names in drop down box
                winCount = Catia.Windows.Count
    
    For i = 1 To winCount
        winName = Catia.Windows.Item(i).Name
            catTargetDrwCbox.AddItem winName
    Next
    
        catTolCbox.AddItem " ±0,1", 0    'catia tolerances
        catTolCbox.AddItem " ±0,2", 1
        catTolCbox.AddItem " ±0,3", 2
        catTolCbox.AddItem " ±0,4", 3
        catTolCbox.AddItem " ±0,5", 4
        catTolCbox.AddItem " ±0,6", 5
        
            XLtolCbox.AddItem " ±0,1", 0
            XLtolCbox.AddItem " ±0,2", 1
            XLtolCbox.AddItem " ±0,3", 2
            XLtolCbox.AddItem " ±0,4", 3
            XLtolCbox.AddItem " ±0,5", 4
            XLtolCbox.AddItem " ±0,6", 5
            
    For s = 1 To selection1.Count
        objName = selection1.Item(s).Value.Name
            lbSelection.AddItem objName
    Next
            
End Sub

Private Sub UserForm_QueryClose(Cancel As Integer, CloseMode As Integer)    'together with cancel button terminates the whole macro
    End
End Sub

Private Sub catPolylineBut_Click()
      targetDrw = catTargetDrwCbox.Value
        headline = catHeadlineTbox.Value
            pointIndex = catPointIndexTbox.Value
                tol = catTolCbox.Value
                    mainDI = catMainDITbox.Value
                        endDI = catEndDITbox.Value
                        
    manX = manXtbox.Value
    manY = manYtbox.Value
    manZ = manZtbox.Value
        
        If catTargetDrwCbox.Value = "" Then    'user feedback controls
            MsgBox "Please select a target drawing!", vbCritical, "Missing information!"
        ElseIf catHeadlineTbox.Value = "" Then
            MsgBox "Please input a table headline!", vbCritical, "Missing information!"
'        ElseIf catPointIndexTbox.Value = "" Then
'            MsgBox "Please input a point index !", vbCritical, "Missing information!"
'        ElseIf catTolCbox.Value = "" Then
'            MsgBox "Please select diameter tolerance!", vbCritical, "Missing information!"
'        ElseIf catMainDITbox.Value = IsNumeric(catMainDITbox.Value) = False Then
'            MsgBox "Please input main diameter!", vbCritical, "Missing information!"
        Else
            'clear old values
            catTargetDrwCbox.Text = ""
            catHeadlineTbox.Text = ""
            catPointIndexTbox.Text = ""
            catTolCbox.Text = ""
            catMainDITbox.Text = ""
            catEndDITbox.Text = ""
                manXtbox.Text = ""
                manYtbox.Text = ""
                manZtbox.Text = ""
                    lbSelection.Value = ""
                    
                    userChoice = 1
            Me.Hide
        End If
End Sub

Private Sub catInvPolylineBut_Click()
    targetDrw = catTargetDrwCbox.Value
        headline = catHeadlineTbox.Value
            pointIndex = catPointIndexTbox.Value
                tol = catTolCbox.Value
                    mainDI = catMainDITbox.Value
                        endDI = catEndDITbox.Value
                        
    manX = manXtbox.Value
    manY = manYtbox.Value
    manZ = manZtbox.Value
    
        If catTargetDrwCbox.Value = "" Then    'user feedback controls
            MsgBox "Please select a target drawing!", vbCritical, "Missing information!"
        ElseIf catHeadlineTbox.Value = "" Then
            MsgBox "Please input a table headline!", vbCritical, "Missing information!"
'        ElseIf catPointIndexTbox.Value = "" Then
'            MsgBox "Please input a point index !", vbCritical, "Missing information!"
'        ElseIf catTolCbox.Value = "" Then
'            MsgBox "Please select diameter tolerance!", vbCritical, "Missing information!"
'        ElseIf catMainDITbox.Value = IsNumeric(catMainDITbox.Value) = False Then
'            MsgBox "Please input main diameter!", vbCritical, "Missing information!"
        Else
            'clear old values
            catTargetDrwCbox.Text = ""
            catHeadlineTbox.Text = ""
            catPointIndexTbox.Text = ""
            catTolCbox.Text = ""
            catMainDITbox.Text = ""
            catEndDITbox.Text = ""
                manXtbox.Text = ""
                manYtbox.Text = ""
                manZtbox.Text = ""
                    lbSelection.Value = ""
                    
                    userChoice = 2
            Me.Hide
        End If
End Sub

Private Sub catPointsBut_Click()
    targetDrw = catTargetDrwCbox.Value
        headline = catHeadlineTbox.Value
            pointIndex = catPointIndexTbox.Value

    manX = manXtbox.Value
    manY = manYtbox.Value
    manZ = manZtbox.Value
        
        If catTargetDrwCbox.Value = "" Then    'user feedback controls
            MsgBox "Please select a target drawing!", vbCritical, "Missing information!"
        ElseIf catHeadlineTbox.Value = "" Then
            MsgBox "Please input a table headline!", vbCritical, "Missing information!"
'        ElseIf catPointIndexTbox.Value = "" Then
'            MsgBox "Please input a point index !", vbCritical, "Missing information!"
        Else
            'clear old values
            catTargetDrwCbox.Text = ""
            catHeadlineTbox.Text = ""
            catPointIndexTbox.Text = ""
            catTolCbox.Text = ""
            catMainDITbox.Text = ""
            catEndDITbox.Text = ""
                manXtbox.Text = ""
                manYtbox.Text = ""
                manZtbox.Text = ""
                    lbSelection.Value = ""
                    
                    userChoice = 3
            Me.Hide
        End If
End Sub

Private Sub catCancelBut_Click()    'closes the form
    Unload Me
End Sub

Private Sub XLPolylineBut_Click()
    headline = XLheadlineTbox.Value
        pointIndex = XLpointIndexTbox.Value
            tol = XLtolCbox.Value
                mainDI = XLmainDITbox.Value
                    endDI = XLendDITbox.Value
                    
    manX = manXtbox.Value
    manY = manYtbox.Value
    manZ = manZtbox.Value
        
        If XLheadlineTbox.Value = "" Then
            MsgBox "Please input a table headline!", vbCritical, "Missing information!"
'        ElseIf XLpointIndexTbox.Value = "" Then
'            MsgBox "Please input a point index!", vbCritical, "Missing information!"
'        ElseIf XLtolCbox.Value = "" Then
'            MsgBox "Please select diameter tolerance!", vbCritical, "Missing information!"
'        ElseIf XLmainDITbox.Value = IsNumeric(XLmainDITbox.Value) = False Then
'            MsgBox "Please input main diameter!", vbCritical, "Missing information!"
        Else
            'clear old values
            XLheadlineTbox.Text = ""
            XLpointIndexTbox.Text = ""
            XLStartPointTBox.Text = ""
            XLtolCbox.Text = ""
            XLmainDITbox.Text = ""
            XLendDITbox.Text = ""
                manXtbox.Text = ""
                manYtbox.Text = ""
                manZtbox.Text = ""
                    lbSelection.Value = ""
                    
                    userChoice = 4
            Me.Hide
        End If
End Sub

Private Sub XLinvPolylineBut_Click()
    headline = XLheadlineTbox.Value
        pointIndex = XLpointIndexTbox.Value
            tol = XLtolCbox.Value
                mainDI = XLmainDITbox.Value
                    endDI = XLendDITbox.Value
            
    manX = manXtbox.Value
    manY = manYtbox.Value
    manZ = manZtbox.Value
        
        If XLheadlineTbox.Value = "" Then
            MsgBox "Please input a table headline!", vbCritical, "Missing information!"
'        ElseIf XLpointIndexTbox.Value = "" Then
'            MsgBox "Please input a point index!", vbCritical, "Missing information!"
'        ElseIf XLtolCbox.Value = "" Then
'            MsgBox "Please select diameter tolerance!", vbCritical, "Missing information!"
'        ElseIf XLmainDITbox.Value = IsNumeric(XLmainDITbox.Value) = False Then
'            MsgBox "Please input main diameter!", vbCritical, "Missing information!"
        Else
            'clear old values
            XLheadlineTbox.Text = ""
            XLpointIndexTbox.Text = ""
            XLStartPointTBox.Text = ""
            XLtolCbox.Text = ""
            XLmainDITbox.Text = ""
            XLendDITbox.Text = ""
                manXtbox.Text = ""
                manYtbox.Text = ""
                manZtbox.Text = ""
                    lbSelection.Value = ""
                    
                    userChoice = 5
            Me.Hide
        End If
End Sub

Private Sub XLpointsBut_Click()
    headline = XLheadlineTbox.Value
        pointIndex = XLpointIndexTbox.Value
            manNum = XLStartPointTBox.Value
            
    manX = manXtbox.Value
    manY = manYtbox.Value
    manZ = manZtbox.Value
        
        If XLheadlineTbox.Value = "" Then
            MsgBox "Please input a table headline!", vbCritical, "Missing information!"
'        ElseIf XLpointIndexTbox.Value = "" Then
'            MsgBox "Please input a point index!", vbCritical, "Missing information!"
        Else
            'clear old values
            XLheadlineTbox.Text = ""
            XLpointIndexTbox.Text = ""
            XLStartPointTBox.Text = ""
            XLtolCbox.Text = ""
            XLmainDITbox.Text = ""
            XLendDITbox.Text = ""
                manXtbox.Text = ""
                manYtbox.Text = ""
                manZtbox.Text = ""
                    lbSelection.Value = ""
                    
                    userChoice = 6
            Me.Hide
        End If
End Sub

Private Sub XLcancelBut_Click()
    Unload Me
End Sub

Attribute VB_Name = "tableMacro"
'****************************************************************************
'This macro creates drawing tables in Catia for selected polyline and points.
'X, Y, Z coordinates, radius for each point and total length of the polyline.

'Instructions for use:
'Select item(s) and run macro, select target drawing, input table headline and letter.
'Table with coordinates will be created in the view "TABLES" on selected drawing.

'Created by Per Björk, Engineering Partner 2014
'****************************************************************************

'variables
Dim Coords(2), TheMeasurable, errorMes As Variant
Dim polyline1NrOfElements As Integer
Dim numberOfPoints As Integer
Dim foundTables As Boolean
Dim errorRep As Boolean

Dim objGEXCELapp As Object
Dim objGEXCELwkBks As Object
Dim objGEXCELwkBk As Object
Dim objGEXCELwkShs As Object
Dim objGEXCELSh As Object

Public selection1 As Selection
Public targetDrw As String
Public headline As String
Public pointIndex As String
Public manNum As Variant
Public tol As String
Public mainDI As String
Public endDI As String
Public userChoice As Integer

Public manX As Variant
Public manY As Variant
Public manZ As Variant

Sub CATMain()
'On Error GoTo errorHandler  'errorhandlng
    
        'Dim selection1 As Selection
        Set selection1 = Catia.ActiveDocument.Selection 'handle the selection in catia
            If selection1.Count = 0 Then    'if selection is empty display message
                MsgBox ("Nothing selected! Please select a polyline or at least one point.")
                    Exit Sub
            End If

                      'load main form
                    mainForm.Show
                    
                    If manX = "" Then
                            manX = 0
                        End If
                            
                            If manY = "" Then
                                manY = 0
                            End If
                        
                                If manZ = "" Then
                                    manZ = 0
                                End If
                                
                                    If manNum = "" Then
                                        manNum = 0
                                    End If
            
                If userChoice = 1 Or userChoice = 2 Then  'user choose to create a polyline table
                    catPolyline
                ElseIf userChoice = 3 Then  'user choose to create a point table
                    catPoints
                ElseIf userChoice = 4 Or userChoice = 5 Then
                    XLpolyline
                ElseIf userChoice = 6 Then
                    XLpoints
                End If

errorHandler:   'error messages
    If Err.Number = -2147467259 Then
        errorMes = MsgBox("No active 3D document!" & vbNewLine & "Load a 3D document and select a polyline or at least one point.", vbCritical, "Error!")
            Err.Number = 0
    End If
End Sub

Sub catPolyline()
    'On Error GoTo errorHandler  'errorhandlng
    
            'handle the selection in catia
            Set selection1 = Catia.ActiveDocument.Selection
                Set polyline1 = selection1.Item(1)  'pick first element (the polyline) of the selection in Catia
                    If polyline1.Type <> "HybridShapePolyline" Then     'check if the object selected is a polyline
                        errorMes = MsgBox("Wrong type of object selected! Please select a polyline.", vbCritical, "Wrong type of object!!")
                        Exit Sub
                    End If
                    
                    Set myPolyline = polyline1.Value
                        polyline1NrOfElements = myPolyline.NumberOfElements  'count number of points in the polyline
'********************************************************************************************************************************
    'start table creation process
    Catia.Windows.Item(targetDrw).Activate     'switch to drawing window
        Set myDoc = Catia.ActiveDocument    'define active document and view
            Set mySheet = myDoc.Sheets.ActiveSheet
    
                For i = 1 To mySheet.Views.Count                'check if drawing view "TABLES" exists
                    Set myView = mySheet.Views.Item(i)      'set view
                        If myView.Name = "TABLES" Then             'if "TABLES" exists activate view and exit for-loop
                            Set myView = mySheet.Views.Item("TABLES")
                                myView.Activate
                                    foundTables = True
                                        Exit For
                        End If
                Next
        
                        If foundTables = False Then             'if "TABLES" doesn't exist, create it and activate
                            Set myView = mySheet.Views.Add("TABLES")
                                myView.Activate
                        End If

        'create the table itself
        Dim mytable As DrawingTable
            Set mytable = myView.Tables.Add(100, 100, polyline1NrOfElements + 2, 6, 7.5, 25)
        
                'add labels
                mytable.SetCellString 1, 1, headline
                mytable.SetCellString 2, 1, "BENDING POINT"
                mytable.SetCellString 2, 2, "X"
                mytable.SetCellString 2, 3, "Y"
                mytable.SetCellString 2, 4, "Z"
                mytable.SetCellString 2, 5, "INNER DI" & tol & "(MM)"
                mytable.SetCellString 2, 6, "R(MM)"
                
                    'format the table
                    mytable.SetColumnSize 1, 44
                    mytable.SetColumnSize 2, 20
                    mytable.SetColumnSize 3, 20
                    mytable.SetColumnSize 4, 20
                    mytable.SetColumnSize 5, 55
                    mytable.SetColumnSize 6, 19
                        mytable.MergeCells 1, 1, 1, 6
                            mytable.SetCellAlignment 1, 1, CatTableTopCenter
                    
'**************************************************************************************************************************************
    'coordinate extraction process
    Dim TheSPAWorkbench As Workbench
        Set TheSPAWorkbench = Catia.ActiveDocument.GetWorkbench("SPAWorkbench") ' set TheSPAWorkbench
    Dim pointRef As Reference
    Dim oRad As Length
'**************************************************************************************************************************************
            
            If userChoice = 1 Then  'normal polyline
                For i = 1 To polyline1NrOfElements       'iterate through all poinst of polyline
                    myPolyline.GetElement i, pointRef, oRad
                            
                    'set refObject
                    Set TheMeasurable = TheSPAWorkbench.GetMeasurable(pointRef)             ' set Measurable with reference
                        TheMeasurable.GetPoint Coords                                           ' get coordinates from Measurable
                    Set MeasureLength = TheSPAWorkbench.GetMeasurable(myPolyline)
                        myPolylineLength = MeasureLength.Length
                        
                    If oRad Is Nothing Then RadiusAtPoint = False Else: RadiusAtPoint = True                ' check if Radius at point
                                       
                    'add point index
                    mytable.SetCellString 2 + i, 1, pointIndex & i
        
                    xPoint = Coords(0)
                    Coords(0) = xPoint + manX
                    xPoint = Round(Coords(0), 1) 'check decimals
                        If xPoint = 0 Then      'avoid division with zero
                            mytable.SetCellString 2 + i, 2, "0,0"       'add "0,0"
                        ElseIf Int(xPoint) / xPoint = 1 Then        'check if integer
                            mytable.SetCellString 2 + i, 2, xPoint & ",0"       'add ",0"
'                        ElseIf Round(Coords(0), 1) / xPoint = 1 Then
'                            MyTable.SetCellString 2 + i, 2, xPoint & "0"    'round second decimal to zero
                        Else
                            mytable.SetCellString 2 + i, 2, Round(Coords(0), 1)     'else, use 1 decimal
                        End If
                    
                    yPoint = Coords(1)
                    Coords(1) = yPoint + manY
                    yPoint = Round(Coords(1), 1)       'same procedure for y and z
                        If yPoint = 0 Then
                            mytable.SetCellString 2 + i, 3, "0,0"
                        ElseIf Int(yPoint) / yPoint = 1 Then
                            mytable.SetCellString 2 + i, 3, yPoint & ",0"
'                        ElseIf Round(Coords(1), 1) / yPoint = 1 Then
'                            MyTable.SetCellString 2 + i, 3, yPoint & "0"
                        Else
                            mytable.SetCellString 2 + i, 3, Round(Coords(1), 1)
                        End If
        
                    zPoint = Coords(2)
                    Coords(2) = zPoint + manZ
                    zPoint = Round(Coords(2), 1)       'same procedure for y and z
                        If zPoint = 0 Then
                            mytable.SetCellString 2 + i, 4, "0,0"
                        ElseIf Int(zPoint) / zPoint = 1 Then
                            mytable.SetCellString 2 + i, 4, zPoint & ",0"
'                        ElseIf Round(Coords(2), 1) / zPoint = 1 Then
'                            MyTable.SetCellString 2 + i, 4, zPoint & "0"
                        Else
                            mytable.SetCellString 2 + i, 4, Round(Coords(2), 1)
                        End If
                                        
                    If RadiusAtPoint Then
                        radPoint = Round(oRad.Value, 0)     'same method as above
                            If radPoint = 0 Then
                                mytable.SetCellString 2 + i, 6, ""
                            ElseIf Int(radPoint) / radPoint = 1 Then
                                mytable.SetCellString 2 + i, 6, radPoint & ""
                            Else
                                mytable.SetCellString 2 + i, 6, Round(oRad.Value, 0)
                            End If
                    End If
                     
                    If mainDI <> "" Then
                        mytable.SetCellString 2 + i, 5, mainDI  'main diameter value
                    End If
                Next
 '**************************************************************************************************************************************************
            ElseIf userChoice = 2 Then  'inverted polyline
                x = 1
                For i = polyline1NrOfElements To 1 Step -1        'iterate through all poinst of polyline
                    myPolyline.GetElement i, pointRef, oRad
                            
                    'set refObject
                    Set TheMeasurable = TheSPAWorkbench.GetMeasurable(pointRef)             ' set Measurable with reference
                        TheMeasurable.GetPoint Coords                                           ' get coordinates from Measurable
                    Set MeasureLength = TheSPAWorkbench.GetMeasurable(myPolyline)
                        myPolylineLength = MeasureLength.Length
                        
                    If oRad Is Nothing Then RadiusAtPoint = False Else: RadiusAtPoint = True                ' check if Radius at point
                    
                    mytable.SetCellString 2 + x, 1, pointIndex & x  'set point ref
            
                        xPoint = Coords(0)
                        Coords(0) = xPoint + manX
                        xPoint = Round(Coords(0), 1) 'check decimals
                            If xPoint = 0 Then      'avoid division with zero
                                mytable.SetCellString (2 + i) - (i - x), 2, "0,0" 'add "0,0"
                            ElseIf Int(xPoint) / xPoint = 1 Then        'check if integer
                                mytable.SetCellString (2 + i) - (i - x), 2, xPoint & ",0"      'add ",00"
'                            ElseIf Round(Coords(0), 1) / xPoint = 1 Then
'                                MyTable.SetCellString (2 + i) - (i - X), 2, xPoint & "0"    'round second decimal to zero
                            Else
                                mytable.SetCellString (2 + i) - (i - x), 2, Round(Coords(0), 1)     'else, use 1 decimal
                            End If
                        
                        yPoint = Coords(1)
                        Coords(1) = yPoint + manY
                        yPoint = Round(Coords(1), 1)       'same procedure for y and z
                            If yPoint = 0 Then
                                mytable.SetCellString (2 + i) - (i - x), 3, "0,0"
                            ElseIf Int(yPoint) / yPoint = 1 Then
                                mytable.SetCellString (2 + i) - (i - x), 3, yPoint & ",0"
'                            ElseIf Round(Coords(1), 1) / yPoint = 1 Then
'                                MyTable.SetCellString (2 + i) - (i - X), 3, yPoint & "0"
                            Else
                                mytable.SetCellString (2 + i) - (i - x), 3, Round(Coords(1), 1)
                            End If
            
                        zPoint = Coords(2)
                        Coords(2) = zPoint + manZ
                        zPoint = Round(Coords(2), 1)       'same procedure for y and z
                            If zPoint = 0 Then
                                mytable.SetCellString (2 + i) - (i - x), 4, "0,0"
                            ElseIf Int(zPoint) / zPoint = 1 Then
                                mytable.SetCellString (2 + i) - (i - x), 4, zPoint & ",0"
'                            ElseIf Round(Coords(2), 1) / zPoint = 1 Then
'                                MyTable.SetCellString (2 + i) - (i - X), 4, zPoint & "0"
                            Else
                                mytable.SetCellString (2 + i) - (i - x), 4, Round(Coords(2), 1)
                            End If
                                            
                        If RadiusAtPoint Then
                            radPoint = Round(oRad.Value, 0)     'same method as above
                                If radPoint = 0 Then
                                    mytable.SetCellString (2 + i) - (i - x), 6, ""
                                ElseIf Int(radPoint) / radPoint = 1 Then
                                    mytable.SetCellString (2 + i) - (i - x), 6, radPoint & ""
                                Else
                                    mytable.SetCellString (2 + i) - (i - x), 6, Round(oRad.Value, 0)
                                End If
                        End If
                    
                    If mainDI <> "" Then
                        mytable.SetCellString (2 + i) - (i - x), 5, mainDI  'main diameter value
                    End If
                        
                    x = x + 1   'add 1 to x for every turn of the loop
                Next
            End If
'****************************************************************************************************************************************
            If endDI = "" Then
                mytable.SetCellString 3, 5, ""   'end point diameter
                mytable.SetCellString polyline1NrOfElements + 2, 5, ""
            Else
                mytable.SetCellString 3, 5, endDI   'end point diameter
                mytable.SetCellString polyline1NrOfElements + 2, 5, endDI
            End If
                  
                MsgBox "Coordinate table completed!"  'display message of completion
'***************************************************************************************************************************************************
errorHandler:   'error messages
    If Err.Number = 438 Then
        errorMes = MsgBox("Can't create drawing table in a 3D document! Please select window containing the target drawing.", vbCritical, "Error!")
            Err.Number = 0
                Exit Sub
    ElseIf Err.Number = -2147467259 Then
        errorMes = MsgBox("Wrong type of object(s) selected! This function only works with point items.", vbCritical, "Error!")
            Err.Number = 0
    End If
End Sub

Sub catPoints()
'On Error GoTo errorHandler  'set up errorhandler

    Dim selection1 As Selection 'handle selection
    Set selection1 = Catia.ActiveDocument.Selection
        numberOfPoints = selection1.Count
    
    'start table creation process
    Catia.Windows.Item(targetDrw).Activate     'switch to drawing window
        Set myDoc = Catia.ActiveDocument    'define active document and view
            Set mySheet = myDoc.Sheets.ActiveSheet
            
    For i = 1 To mySheet.Views.Count                'check if drawing view "TABLES" exists
        Set myView = mySheet.Views.Item(i)      'set view
            If myView.Name = "TABLES" Then             'if "TABLES" exists activate view and exit for loop
                Set myView = mySheet.Views.Item("TABLES")
                    myView.Activate
                        foundTables = True
                            Exit For
            End If
    Next
        
            If foundTables = False Then             'if "TABLES" doesn't exist, create and activate it
                Set myView = mySheet.Views.Add("TABLES")
                    myView.Activate
            End If
        
        'create the table itself
        Set mytable = myView.Tables.Add(100, 100, numberOfPoints + 2, 4, 7.5, 23)
        'add labels
        mytable.SetCellString 1, 1, headline
        mytable.SetCellString 2, 1, "REF.POINT"
        mytable.SetCellString 2, 2, "X"
        mytable.SetCellString 2, 3, "Y"
        mytable.SetCellString 2, 4, "Z"
            'format things
            mytable.SetColumnSize 1, 44
            mytable.SetColumnSize 2, 35
            mytable.MergeCells 1, 1, 1, 4
            mytable.SetCellAlignment 1, 1, CatTableTopCenter
        
'**********************************************************************************************************************************************
    'coordinate extraction
    Dim TheSPAWorkbench As Workbench
    Set TheSPAWorkbench = Catia.ActiveDocument.GetWorkbench("SPAWorkbench") ' set TheSPAWorkbench
    
    For i = 1 To numberOfPoints                 'create correct number of rows
        Set Element = selection1.Item(i)
            Set selPoint = Element.Value
        
        Set TheMeasurable = TheSPAWorkbench.GetMeasurable(selPoint)
            TheMeasurable.GetPoint Coords       'get coordinates from Measurable
            
                mytable.SetCellString 2 + i, 1, pointIndex & i  'add point index
            
                xPoint = Coords(0)
                Coords(0) = xPoint + manX
                xPoint = Round(Coords(0), 1) 'check decimals
                    If xPoint = 0 Then  'avoid division with zero
                        mytable.SetCellString 2 + i, 2, "0,0"   'add 0,0
                    ElseIf Int(xPoint) / xPoint = 1 Then        'if integer
                        mytable.SetCellString 2 + i, 2, xPoint & ",0"       'add ",0"
'                    ElseIf Round(Coords(0), 1) / xPoint = 1 Then
'                            MyTable.SetCellString 2 + i, 2, xPoint & "0"
                    Else
                        mytable.SetCellString 2 + i, 2, Round(Coords(0), 1)     'else, use 1 decimal
                    End If
                
                yPoint = Coords(1)
                Coords(1) = yPoint + manY
                yPoint = Round(Coords(1), 1)       'same procedure for y and z
                        
                    If yPoint = 0 Then
                        mytable.SetCellString 2 + i, 3, "0,0"
                    ElseIf Int(yPoint) / yPoint = 1 Then
                        mytable.SetCellString 2 + i, 3, yPoint & ",0"
'                    ElseIf Round(Coords(1), 1) / yPoint = 1 Then
'                            MyTable.SetCellString 2 + i, 3, yPoint & "0"
                    Else
                        mytable.SetCellString 2 + i, 3, Round(Coords(1), 1)
                    End If

                zPoint = Coords(2)
                Coords(2) = zPoint + manZ
                zPoint = Round(Coords(2), 1)       'same procedure for y and z
                    If zPoint = 0 Then
                        mytable.SetCellString 2 + i, 4, "0,0"
                    ElseIf Int(zPoint) / zPoint = 1 Then
                        mytable.SetCellString 2 + i, 4, zPoint & ",0"
'                    ElseIf Round(Coords(2), 1) / zPoint = 1 Then
'                            MyTable.SetCellString 2 + i, 4, zPoint & "0"
                    Else
                        mytable.SetCellString 2 + i, 4, Round(Coords(2), 1)
                    End If
        Next
        
        MsgBox "Coordinate table completed!" & vbNewLine & "Points are presented in order of selection."  'display message of completion
'***************************************************************************************************************************************************
errorHandler:   'error messages
    If Err.Number = 438 Then
        errorMes = MsgBox("Can't create drawing table in a 3D document! Please select window containing the target drawing.", vbCritical, "Error")
            Err.Number = 0
    ElseIf Err.Number = -2147467259 Then
        errorMes = MsgBox("Wrong type of object(s) selected! This function only works with point items.", vbCritical, "Error!")
            Err.Number = 0
    End If
End Sub

Sub XLpolyline()
'On Error GoTo errorHandler
    
        'handle the selection in catia
        Set selection1 = Catia.ActiveDocument.Selection
            Set polyline1 = selection1.Item(1)  'pick first element (the polyline) of the selection in Catia
                If polyline1.Type <> "HybridShapePolyline" Then     'check if the object selected is a polyline
                        errorMes = MsgBox("Wrong type of object selected! Please select a polyline.", vbCritical, "Wrong type of object!!")
                    Exit Sub
                End If
            Set myPolyline = polyline1.Value
                polyline1NrOfElements = myPolyline.NumberOfElements  'count number of points in the polyline
'************************************************************************************************************************************************
        StartEXCEL  'run Excel
        
        Dim TheSPAWorkbench As Workbench
        Set TheSPAWorkbench = Catia.ActiveDocument.GetWorkbench("SPAWorkbench") 'set TheSPAWorkbench
            Dim pointRef As Reference
                Dim oRad  As Length
'************************************************************************************************************************************************
    If userChoice = 4 Then    'normal polyline
        For i = 1 To polyline1NrOfElements  'iterate through all poinst of polyline
            myPolyline.GetElement i, pointRef, oRad
                
                Set TheMeasurable = TheSPAWorkbench.GetMeasurable(pointRef)
                    TheMeasurable.GetPoint Coords                                           'get coordinates from Measurable
                Set MeasureLength = TheSPAWorkbench.GetMeasurable(myPolyline)
                    myPolylineLength = MeasureLength.Length

            If oRad Is Nothing Then RadiusAtPoint = False Else RadiusAtPoint = True ' check if Radius at point
             
            'write data to Excel sheet
            objGEXCELSh.cells(i + 2, "A") = pointIndex & i      'add point name

            xPoint = Coords(0)
            Coords(0) = xPoint + manX
            xPoint = Round(Coords(0), 1) 'check decimals
                If xPoint = 0 Then      'prevent divison by zero
                    objGEXCELSh.cells(i + 2, "B") = "0,0"       'add "0,0"
                ElseIf Int(xPoint) / xPoint = 1 Then        'check if integer
                    objGEXCELSh.cells(i + 2, "B") = xPoint & ",00"       'add ",0"
'                ElseIf Round(Coords(0), 1) / xPoint = 1 Then
'                    objGEXCELSh.cells(i + 2, "B") = xPoint & "0"       'add "0"
                Else
                    objGEXCELSh.cells(i + 2, "B") = Round(Coords(0), 1) 'else, use 1 decimal
                End If
                
            yPoint = Coords(1)
            Coords(1) = yPoint + manY
            yPoint = Round(Coords(1), 1)       'same procedure for y and z
                If yPoint = 0 Then
                    objGEXCELSh.cells(i + 2, "C") = "0,0"
                ElseIf Int(yPoint) / yPoint = 1 Then
                    objGEXCELSh.cells(i + 2, "C") = yPoint & ",0"
'                ElseIf Round(Coords(1), 1) / yPoint = 1 Then
'                    objGEXCELSh.cells(i + 2, "C") = yPoint & "0"       'add "0"
                Else
                    objGEXCELSh.cells(i + 2, "C") = Round(Coords(1), 1)
                End If
    
            zPoint = Coords(2)
            Coords(2) = zPoint + manZ
            zPoint = Round(Coords(2), 1)       'same procedure for y and z
                If zPoint = 0 Then
                    objGEXCELSh.cells(i + 2, "D") = "0,0"
                ElseIf Int(zPoint) / zPoint = 1 Then
                    objGEXCELSh.cells(i + 2, "D") = zPoint & ",0"
'                ElseIf Round(Coords(2), 1) / zPoint = 1 Then
'                    objGEXCELSh.cells(i + 2, "D") = zPoint & "0"       'add "0"
                Else
                    objGEXCELSh.cells(i + 2, "D") = Round(Coords(2), 1)
                End If
                
                    If RadiusAtPoint Then   'add radius value
                        radPoint = Round(oRad.Value, 0)     'same method as above
                            If radPoint = 0 Then
                                objGEXCELSh.cells(i + 2, "F") = ""
                            ElseIf Int(radPoint) / radPoint = 1 Then
                                objGEXCELSh.cells(i + 2, "F") = radPoint
                            Else
                                objGEXCELSh.cells(i + 2, "F") = Round(oRad.Value, 0)
                            End If
                    End If
                    
                If mainDI <> "" Then
                    objGEXCELSh.cells(i + 2, "E") = mainDI
                End If
        Next
 '***********************************************************************************************************
    ElseIf userChoice = 5 Then    'inverted polyline
        x = 1
        For i = polyline1NrOfElements To 1 Step -1  'iterate through all poinst of polyline
            
                myPolyline.GetElement i, pointRef, oRad
                    
                    Set TheMeasurable = TheSPAWorkbench.GetMeasurable(pointRef)
                        TheMeasurable.GetPoint Coords                       'get coordinates from Measurable
                    Set MeasureLength = TheSPAWorkbench.GetMeasurable(myPolyline)
                        myPolylineLength = MeasureLength.Length
    
                If oRad Is Nothing Then RadiusAtPoint = False Else RadiusAtPoint = True ' check if Radius at point
                 
                'write data to Excel sheet
                objGEXCELSh.cells(x + 2, "A") = pointIndex & x      'add point name
    
            xPoint = Coords(0)
            Coords(0) = xPoint + manX
            xPoint = Round(Coords(0), 1) 'check decimals
                If xPoint = 0 Then      'prevent divison by zero
                    objGEXCELSh.cells((2 + i) - (i - x), "B") = "0,0"       'add "0,0"
                ElseIf Int(xPoint) / xPoint = 1 Then        'check if integer
                    objGEXCELSh.cells((2 + i) - (i - x), "B") = xPoint & ",0"       'add ",0"
'                ElseIf Round(Coords(0), 1) / xPoint = 1 Then
'                    objGEXCELSh.cells((2 + i) - (i - X), "B") = xPoint & "0"       'add "0"
                Else
                    objGEXCELSh.cells((2 + i) - (i - x), "B") = Round(Coords(0), 1) 'else, use 1 decimal
                End If
                
            yPoint = Coords(1)
            Coords(1) = yPoint + manY
            yPoint = Round(Coords(1), 1)       'same procedure for y and z
                If yPoint = 0 Then
                    objGEXCELSh.cells((2 + i) - (i - x), "C") = "0,0"
                ElseIf Int(yPoint) / yPoint = 1 Then
                    objGEXCELSh.cells((2 + i) - (i - x), "C") = yPoint & ",0"
'                ElseIf Round(Coords(1), 1) / yPoint = 1 Then
'                    objGEXCELSh.cells((2 + i) - (i - X), "C") = yPoint & "0"
                Else
                    objGEXCELSh.cells((2 + i) - (i - x), "C") = Round(Coords(1), 1)
                End If
    
            zPoint = Coords(2)
            Coords(2) = zPoint + manZ
            zPoint = Round(Coords(2), 1)       'same procedure for y and z
                If zPoint = 0 Then
                    objGEXCELSh.cells((2 + i) - (i - x), "D") = "0,0"
                ElseIf Int(zPoint) / zPoint = 1 Then
                    objGEXCELSh.cells((2 + i) - (i - x), "D") = zPoint & ",0"
'                ElseIf Round(Coords(2), 1) / zPoint = 1 Then
'                    objGEXCELSh.cells((2 + i) - (i - X), "D") = zPoint & "0"
                Else
                    objGEXCELSh.cells((2 + i) - (i - x), "D") = Round(Coords(2), 1)
                End If
                
                    If RadiusAtPoint Then   'add radius value
                        radPoint = Round(oRad.Value, 2)     'same method as above
                            If radPoint = 0 Then
                                objGEXCELSh.cells((2 + i) - (i - x), "F") = ""
                            ElseIf Int(radPoint) / radPoint = 1 Then
                                objGEXCELSh.cells((2 + i) - (i - x), "F") = radPoint
                            Else
                                objGEXCELSh.cells((2 + i) - (i - x), "F") = Round(oRad.Value, 0)
                            End If
                    End If
        
        If mainDI <> "" Then
            objGEXCELSh.cells((2 + i) - (i - x), "E") = mainDI
        End If
        
        x = x + 1   'add 1 to x for every turn of the loop
        Next
    End If
            
            If endDI = "" Then
                objGEXCELSh.cells(3, "E") = ""
                objGEXCELSh.cells(polyline1NrOfElements + 2, "E") = ""
            Else
                objGEXCELSh.cells(3, "E") = endDI
                objGEXCELSh.cells(polyline1NrOfElements + 2, "E") = endDI
            End If
            
            MsgBox "Coordinate extraction complete!"       'completion message
'**********************************************************************************************************************************************************
errorHandler:   'error messages
    If Err.Number = -2147467259 Then
        errorMes = MsgBox("Wrong type of object(s) selected! This function only works with point items.", vbCritical, "Error!")
            Err.Number = 0
    End If
End Sub

Sub XLpoints()
    'On Error GoTo errorHandler  'errorhandler
    
        'set up selection
        Dim selection1 As Selection
        Set selection1 = Catia.ActiveDocument.Selection
            numberOfPoints = selection1.Count
'*******************************************************************************************************************
    StartEXCEL
'*******************************************************************************************************************
    Dim TheSPAWorkbench As Workbench
    Set TheSPAWorkbench = Catia.ActiveDocument.GetWorkbench("SPAWorkbench")     'set TheSPAWorkbench
  
    For i = 1 To selection1.Count       'go through the selected points
        Set Element = selection1.Item(i)
            Set selPoint = Element.Value
        
            Set TheMeasurable = TheSPAWorkbench.GetMeasurable(selPoint)
                TheMeasurable.GetPoint Coords              'get coordinates from Measurable
                
        If manNum = 0 Then
                objGEXCELSh.cells(i + 2, "A") = pointIndex & i  'add point prefix
        Else
            objGEXCELSh.cells(i + 2, "A") = pointIndex & manNum 'add the optional numbering
                manNum = manNum + 1     'increase by one
        End If
        
        xPoint = Coords(0)
        Coords(0) = xPoint + manX
        xPoint = Round(Coords(0), 1) 'check decimals
            If xPoint = 0 Then      'prevent division by zero
                objGEXCELSh.cells(i + 2, "B") = "0,0"       'add "0,0"
            ElseIf Int(xPoint) / xPoint = 1 Then        'check if integer
                objGEXCELSh.cells(i + 2, "B") = xPoint & ",0"       'add ",0"
'            ElseIf Round(Coords(0), 1) / xPoint = 1 Then
'                    objGEXCELSh.cells(i + 2, "B") = xPoint & "0"    'add "0"
            Else
                objGEXCELSh.cells(i + 2, "B") = Round(Coords(0), 1) 'else, use 1 decimal
            End If
            
        yPoint = Coords(1)
        Coords(1) = yPoint + manY
        yPoint = Round(Coords(1), 1)       'same procedure for y and z
            If yPoint = 0 Then
                objGEXCELSh.cells(i + 2, "C") = "0,0"
            ElseIf Int(yPoint) / yPoint = 1 Then
                objGEXCELSh.cells(i + 2, "C") = yPoint & ",0"
'            ElseIf Round(Coords(1), 1) / yPoint = 1 Then
'                    objGEXCELSh.cells(i + 2, "C") = yPoint & "0"
            Else
                objGEXCELSh.cells(i + 2, "C") = Round(Coords(1), 1)
            End If

        zPoint = Coords(2)
        Coords(2) = zPoint + manZ
        zPoint = Round(Coords(2), 1)       'same procedure for y and z
            If zPoint = 0 Then
                objGEXCELSh.cells(i + 2, "D") = "0,0"
            ElseIf Int(zPoint) / zPoint = 1 Then
                objGEXCELSh.cells(i + 2, "D") = zPoint & ",0"
'            ElseIf Round(Coords(2), 1) / zPoint = 1 Then
'                    objGEXCELSh.cells(i + 2, "D") = zPoint & "0"
            Else
                objGEXCELSh.cells(i + 2, "D") = Round(Coords(2), 1)
            End If
    Next
            MsgBox "Coordinate extraction complete!" & vbNewLine & "Points are presented in order of selection."    'display completion message
'**************************************************************************************************************************************************
errorHandler:   'error message
    If Err.Number = -2147467259 Then
        errorMes = MsgBox("Wrong type of object(s) selected! This function only works with point items.", vbCritical, "Error!")
            Err.Number = 0
    End If
    
End Sub

Sub StartEXCEL()    'function for opening excel
    Err.Clear
        On Error Resume Next    'error handling
            Set objGEXCELapp = GetObject(, "EXCEL.Application")     'start Excel

    If Err.Number <> 0 Then
        Err.Clear
            Set objGEXCELapp = CreateObject("EXCEL.Application")
    End If
'*****************************************************************************************************************
    objGEXCELapp.Application.Visible = True
        Set objGEXCELwkBks = objGEXCELapp.Application.WorkBooks     'prepare excel worksheets
        Set objGEXCELwkBk = objGEXCELwkBks.Add
        Set objGEXCELwkShs = objGEXCELwkBk.Worksheets(1)
        Set objGEXCELSh = objGEXCELwkBk.Sheets(1)
            objGEXCELSh.cells(1, "A") = headline         'add table headlines
            objGEXCELSh.cells(2, "A") = "REF.POINT"
            objGEXCELSh.cells(2, "B") = "X"
            objGEXCELSh.cells(2, "C") = "Y"
            objGEXCELSh.cells(2, "D") = "Z"
            
            If userChoice <> 6 Then   'add only for polylines
                objGEXCELSh.cells(2, "A") = "BENDING POINT"
                objGEXCELSh.cells(2, "E") = "INNER DI" & tol & "(MM)"
                objGEXCELSh.cells(2, "F") = "R(MM)"
            End If
End Sub
