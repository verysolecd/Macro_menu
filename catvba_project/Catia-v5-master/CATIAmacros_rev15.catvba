Attribute VB_Name = "addLeaders3DPMI"
'Macro created by Per Björk, Engineering Partner
'This macro creates text labels with leaders for selected 3D points in 3DPMI documents.

'Variables
Dim strFilePath As String
Dim objFile As File
Dim objTextStream As TextStream
Dim strLine As String

Public ParentHB As HybridBody
Public CompGeom
Public part1 As Part
Public targetPart As String
Public indexL As String
Public indexN As Integer
Public parentName As String

Dim xMove As Integer
'Dim Coords(2) As Variant
Dim TheMeasurable As Variant
Dim numberOfPoints As Integer
Dim pointName As String
Dim objPart As Part
Dim partName As String
Dim oPartName As String
Dim nPartName As String

Sub CATMain()
    On Error GoTo errorHandler:
    xMove = 0
    
        Dim Selection1 As Selection
        Set Selection1 = CATIA.ActiveDocument.Selection 'handle the selection in catia
                numberOfPoints = Selection1.Count
                    
                    If numberOfPoints = 0 Then    'if selection is empty display message
                        MsgBox "Nothing selected! Please select at least one datum point.", vbCritical, "Empty selection!"
                            Exit Sub
                    End If
            
        'handle the selection in catia
        Set point1 = Selection1.Item(1)  'pick first element (the point) of the selection in Catia
            If point1.Type <> "HybridShapePointExplicit" Then     'check if the object selected is a dautm point
                errorMes = MsgBox("Wrong type of object selected! Please only select datum points.", vbCritical, "Wrong type of object!!")
                    Exit Sub
            End If

        leaderForm.Show     'show form
        
            Set objPart = GetPartFromObject(point1.Value)
            
            oPartName = objPart.Name      'get the partname
            nPartName = Left(oPartName, Len(oPartName) - 2) & ".CATPart"      'remove last two characters and add ".CATPart" to the end
            
            Dim documents1 As Documents     'all the iterations for Catia to reach down into the feature tree
            Set documents1 = CATIA.Documents
        
            Dim partDocument1 As PartDocument
            Set partDocument1 = documents1.Item(nPartName)
            
            Set part1 = partDocument1.Part
        
            Dim annotationSets1 As AnnotationSets
            Set annotationSets1 = part1.AnnotationSets
        
            Dim annotationSet1 As AnnotationSet
            Set annotationSet1 = annotationSets1.Add("VCS_ISO_3D_ASSY")
                    
                getHybridParent point1.Value   'find geometric set

                Dim hybridShapes1 As HybridShapes
                Set hybridShapes1 = ParentHB.HybridShapes
                
'                hybridCount = hybridShapes1.Count
'
'                For h = 1 To hybridCount
'                    MsgBox hybridShapes1.Item(h).Name
'                Next
                
'**************************************************************************************************************************************
        'coordinate extraction process
        Dim TheSPAWorkbench As Workbench
        Set TheSPAWorkbench = CATIA.ActiveDocument.GetWorkbench("SPAWorkbench") ' set TheSPAWorkbench
        Dim pointRef As Reference
                
    '**************************************************************************************************************************************
            
            
            For i = 1 To numberOfPoints       'iterate through all points of polyline
                'MsgBox pointRef.Name
                Set Element = Selection1.Item(i)
                    Set selPoint = Element.Value
        
'        Set TheMeasurable = TheSPAWorkbench.GetMeasurable(selPoint)
'            TheMeasurable.GetPoint Coords       'get coordinates from Measurable
'
'                xPoint = Coords(0)
'                    'MsgBox xPoint
'
'                yPoint = Coords(1)
'                    'MsgBox yPoint
'
'                zPoint = Coords(2)
'                    'MsgBox zPoint
                    
                    pointName = hybridShapes1.Item(i).Name
                    
                    Dim HybridShapePoint1 As HybridShapePointExplicit
                    Set HybridShapePoint1 = hybridShapes1.Item(pointName)
                    
                    Dim reference1 As Reference
                    Set reference1 = part1.CreateReferenceFromObject(HybridShapePoint1)

                    Dim userSurfaces1 As UserSurfaces
                    Set userSurfaces1 = part1.UserSurfaces

                    Dim bSTR1 As String
                    bSTR1 = part1.Name

                    Dim userSurface1 As UserSurface     'set up target surface for each point
                    Set userSurface1 = userSurfaces1.Generate(reference1)
                    
                    Dim annotationFactory1 As AnnotationFactory     'set up annotations
                    Set annotationFactory1 = annotationSet1.AnnotationFactory
                    
                    Dim annotation1 As Annotation
                    Set annotation1 = annotationFactory1.CreateEvoluateText(userSurface1, xMove, -3700, 0, True)    'create the  annotation
                                     
                    annotation1.Text.Text = indexL & indexN

                    annotation1.Text.Get2dAnnot.leaders.Item(1).HeadSymbol = catFilledArrow  'define the leader headsymbol, a filled arrow
                    'annotation1.Text.Get2dAnnot.ActivateFrame (catRectangle)
                                        
                    indexN = indexN + 1
                    xMove = xMove + 100
                    
            Next
            
        part1.Update    'update the part document
            
    MsgBox "Leaders created!"  'display message of completion
'***************************************************************************************************************************************************
errorHandler:           'error messages
'    MsgBox "The most recent error number is " & Err & _
'          ". Its message text is: " & Error(Err)

    If Err.Number = -2147467259 Then
        errorMes = MsgBox("You have to select points from the feature tree.", vbCritical, "Error!")
            Err.Number = 0
    End If
End Sub

Function GetPartFromObject(ByRef iObject As Object) As Part
    'This function calls itself recursively to access the
    'parent of the object passed in until a Part object
    'is reached.
    Dim strType As String
        'Get the type of the object passed into the function
        strType = TypeName(iObject)
            If strType = "Part" Then
                'If the object passed in is a part, return it and exit
                Set GetPartFromObject = iObject
                    Exit Function
            ElseIf strType = TypeName(iObject.Parent) Then
                'If the type of this object is the same as the parent object
                'then return nothing. The reason is the Parent property of
                'some objects simply returns the same object. This will never
                'get us to the part and will result in an infinite loop.
                'Example object types are Reference and Resource among others
                Set GetPartFromObject = Nothing
                    Exit Function
            Else
                'Call the function again and pass it the object’s parent
                Set GetPartFromObject = GetPartFromObject(iObject.Parent)
            End If
End Function

Function getHybridParent(InputGeom As HybridShape) As HybridBody
    Dim CurHBs As HybridBodies
    Set CurHBs = part1.HybridBodies
        Set CompGeom = InputGeom
            For v = 1 To CurHBs.Count
                RecHB CurHBs.Item(v)
                    If Not ParentHB Is Nothing Then
                        Set getHybridParent = ParentHB
                            Exit Function
                    End If
            Next v
End Function

Sub RecHB(inputHb As HybridBody)
    If inputHb.HybridBodies.Count <> 0 And Not CompGeom Is Nothing Then
         For XX = 1 To inputHb.HybridBodies.Count       'first level
             For YY = 1 To inputHb.HybridBodies.Item(XX).HybridBodies.Count     'second level
                If inputHb.HybridBodies.Item(XX).HybridBodies.Item(YY).Name = CompGeom.Name Then
                    Set ParentHB = inputHb.HybridBodies.Item(XX)
                        Set CompGeom = Nothing
                        Exit Sub
                End If

                If CompGeom Is Nothing Then
                    Exit Sub
                End If
            Next YY

            For YY = 1 To inputHb.HybridBodies.Item(XX).HybridShapes.Count  'next level
                If inputHb.HybridBodies.Item(XX).HybridShapes.Item(YY).Name = CompGeom.Name Then
                    Set ParentHB = inputHb.HybridBodies.Item(XX)
                        Set CompGeom = Nothing
                            Exit Sub
                End If

                If CompGeom Is Nothing Then
                    Exit Sub
                End If
            Next YY

            RecHB inputHb.HybridBodies.Item(XX)     'call the function again
            If CompGeom Is Nothing Then
                Exit Sub
            End If
        Next XX
    End If
End Sub

Attribute VB_Name = "addTable3DPMI"
'Macro created by Per Björk, Engineering Partner
'This macro inserts a table in 3DPMI document.

'Variables
Dim strFilePath As String
Dim objFile As File
Dim objTextStream As TextStream
Dim strLine As String

Public ParentHB As HybridBody
Public CompGeom
Public part1 As Part
Public targetPart As String
Public parentName As String

Dim objPart As Part
Dim partName As String
Dim oPartName As String
Dim nPartName As String
Dim numberOfItems As Integer

Sub CATMain()
    On Error GoTo errorHandler:
        
        Dim Selection1 As Selection
        Set Selection1 = CATIA.ActiveDocument.Selection 'handle the selection in catia
                numberOfItems = Selection1.Count
                    
                    If numberOfItems = 0 Then    'if selection is empty display message
                        MsgBox "Nothing selected!" & vbNewLine & "Please select an item from a Geometrical set to be used as reference.", vbCritical, "No reference!"
                            Exit Sub
                    End If
            
        Set selObj = Selection1.Item(1)
        
        Dim myObj As HybridShape
        Set myObj = selObj.Value
        
            Set objPart = GetPartFromObject(myObj)
            
            oPartName = objPart.Name      'get the partname
            nPartName = Left(oPartName, Len(oPartName) - 2) & ".CATPart"      'remove last two characters and add ".CATPart" to the end
            
            Dim documents1 As Documents     'all the iterations for Catia to reach down into the feature tree
            Set documents1 = CATIA.Documents
        
            Dim partDocument1 As PartDocument
            Set partDocument1 = documents1.Item(nPartName)
            
            Set part1 = partDocument1.Part
        
            Dim annotationSets1 As AnnotationSets
            Set annotationSets1 = part1.AnnotationSets
        
            Dim annotationSet1 As AnnotationSet
            Set annotationSet1 = annotationSets1.Add("VCS_ISO_3D_ASSY")
                                
                getHybridParent myObj   'find geometric set
    
                Dim hybridShapes1 As HybridShapes
                Set hybridShapes1 = ParentHB.HybridShapes
                
    '                hybridCount = hybridShapes1.Count
    '
    '                For h = 1 To hybridCount
    '                    MsgBox hybridShapes1.Item(h).Name '
            
                Dim HybridShape1 As HybridShape
                Set HybridShape1 = hybridShapes1.Item(myObj.Name)
                
                    Dim reference1 As Reference
                    Set reference1 = part1.CreateReferenceFromObject(HybridShape1)
        
                    Dim userSurfaces1 As UserSurfaces
                    Set userSurfaces1 = part1.UserSurfaces
        
                    Dim bSTR1 As String
                    bSTR1 = part1.Name
        
                    Dim userSurface1 As UserSurface     'set up target surface for each point
                    Set userSurface1 = userSurfaces1.Generate(reference1)
                    
                    'set up for the table
                    Dim annotationFactory1 As AnnotationFactory     'set up annotations
                    Set annotationFactory1 = annotationSet1.AnnotationFactory
                    
                    Dim annotation1 As Annotation
                    Set annotation1 = annotationFactory1.CreateText(userSurface1)
                
                        'Display file open dialog
                        strFilePath = CATIA.FileSelectionBox("Please select a *.prn file", "*.prn", 0)
                         
                        'If user clicked cancel (empty string is returned), then exit the program
                        If strFilePath = "" Then Exit Sub
                         
                        'Open the file, read the first line then close the file
                        Set objFile = CATIA.FileSystem.GetFile(strFilePath)
                        Set objTextStream = objFile.OpenAsTextStream("ForReading")
                        
                        strLine = objTextStream.Read(10000)
                        objTextStream.Close
                         
                        'Display the read text value…just to show it was read.
                        'MsgBox "First line: " & strLine, 0, "Text File Content"
            
                        annotation1.Text.Text = strLine
                        annotation1.Text.Get2dAnnot.ActivateFrame (catRectangle)
                                      
            part1.Update    'update the part document
                
        MsgBox "Table added!" 'display message of completion
'***************************************************************************************************************************************************
errorHandler:           'error messages
'    MsgBox "The most recent error number is " & Err & _
'          ". Its message text is: " & Error(Err)

    If Err.Number = 13 Then
        errorMes = MsgBox("You have to select an item from a Geometrical set.", vbCritical, "Error!")
            Err.Number = 0
    End If
End Sub

Function GetPartFromObject(ByRef iObject As Object) As Part
    'This function calls itself recursively to access the
    'parent of the object passed in until a Part object
    'is reached.
    Dim strType As String
        'Get the type of the object passed into the function
        strType = TypeName(iObject)
            If strType = "Part" Then
                'If the object passed in is a part, return it and exit
                Set GetPartFromObject = iObject
                    Exit Function
            ElseIf strType = TypeName(iObject.Parent) Then
                'If the type of this object is the same as the parent object
                'then return nothing. The reason is the Parent property of
                'some objects simply returns the same object. This will never
                'get us to the part and will result in an infinite loop.
                'Example object types are Reference and Resource among others
                Set GetPartFromObject = Nothing
                    Exit Function
            Else
                'Call the function again and pass it the object’s parent
                Set GetPartFromObject = GetPartFromObject(iObject.Parent)
            End If
End Function

Function getHybridParent(InputGeom As HybridShape) As HybridBody
    Dim CurHBs As HybridBodies
    Set CurHBs = part1.HybridBodies
        Set CompGeom = InputGeom
            For v = 1 To CurHBs.Count
                RecHB CurHBs.Item(v)
                    If Not ParentHB Is Nothing Then
                        Set getHybridParent = ParentHB
                            Exit Function
                    End If
            Next v
End Function

Sub RecHB(inputHb As HybridBody)
    If inputHb.HybridBodies.Count <> 0 And Not CompGeom Is Nothing Then
         For XX = 1 To inputHb.HybridBodies.Count       'first level
             For YY = 1 To inputHb.HybridBodies.Item(XX).HybridBodies.Count     'second level
                If inputHb.HybridBodies.Item(XX).HybridBodies.Item(YY).Name = CompGeom.Name Then
                    Set ParentHB = inputHb.HybridBodies.Item(XX)
                        Set CompGeom = Nothing
                        Exit Sub
                End If

                If CompGeom Is Nothing Then
                    Exit Sub
                End If
            Next YY

            For YY = 1 To inputHb.HybridBodies.Item(XX).HybridShapes.Count  'next level
                If inputHb.HybridBodies.Item(XX).HybridShapes.Item(YY).Name = CompGeom.Name Then
                    Set ParentHB = inputHb.HybridBodies.Item(XX)
                        Set CompGeom = Nothing
                            Exit Sub
                End If

                If CompGeom Is Nothing Then
                    Exit Sub
                End If
            Next YY

            RecHB inputHb.HybridBodies.Item(XX)     'call the function again
            If CompGeom Is Nothing Then
                Exit Sub
            End If
        Next XX
    End If
End Sub

Attribute VB_Name = "bulkRenamePoints"
Sub CATMain()
    'variables
    Dim selectedPoints As Selection
    Dim pointLetter As String
    Dim startNum As Variant
    Dim numberOfPoints As Integer
    
    On Error GoTo errorHandler
     
    Set selectedPoints = CATIA.ActiveDocument.Selection 'handle the selection in catia
            numberOfPoints = selectedPoints.Count
                
                If numberOfPoints = 0 Then    'if selection is empty display message
                    MsgBox "Nothing selected! Please select at least one point.", vbCritical, "Empty selection!"
                        Exit Sub
                End If
                    
    renameForm.Show
    
    If startNum = "" Then
        startNum = 1
    End If
    
        For i = 1 To numberOfPoints
            'MsgBox selectedPoints.Item(i).Value.Name
            selectedPoints.Item(i).Value.Name = pointLetter & startNum
                startNum = startNum + 1
        Next
        
    MsgBox "Renaming complete!"
        
'***************************************************************************************************************************************************
errorHandler:           'error messages
'    MsgBox "The most recent error number is " & Err & _
'          ". Its message text is: " & Error(Err)

    If Err.Number = -2147467259 Then
        errorMes = MsgBox("You have to select points from the feature tree.", vbCritical, "Error!")
            Err.Number = 0
    End If
End Sub

Attribute VB_Name = "extractTable"
'This macro extracts values from Catia tables and puts them in a Excel file

'variables
Dim Selection1 As Selection
Dim nrOfColumns As Long
Dim nrOfRows, movedCol As Long
Dim cellContent As String

Dim objGEXCELapp As Object
Dim objGEXCELwkBks As Object
Dim objGEXCELwkBk As Object
Dim objGEXCELwkShs As Object
Dim objGEXCELSh As Object

Sub CATMain()
    On Error Resume Next

    Set Selection1 = CATIA.ActiveDocument.Selection
        If Selection1.Count = 0 Then    'if selection is empty display message
            MsgBox "Nothing selected! Please select a drawing table.", vbCritical, "Empty selection!!"
                Exit Sub
                
        ElseIf Selection1.Item(1).Type <> "DrawingTable" Then   'if no drawing table is selected display message
            MsgBox "Wrong type of object selected! Please select a drawingtable.", vbCritical, "Wrong type of object!!"
                Exit Sub
        End If
        
            Dim myTable As DrawingTable     'define table
            Set myTable = Selection1.Item(1).Value
            
                nrOfColumns = myTable.NumberOfColumns   'get number of columns & rows
                nrOfRows = myTable.NumberOfRows
                
'                MsgBox "#Columns: " & nrOfColumns & vbNewLine & _
'                "#Rows: " & nrOfRows
    
    StartEXCEL  'launch Excel
    
    For row = 1 To nrOfRows         'iterate every row
        movedCol = 1    'star counting from 1
        For col = 1 To nrOfColumns      'iterate for every column of that row
            cellContent = myTable.GetCellString(row, col)   'copy data from cell in Catia
                
                If col = 1 Then     'first column position is unchanged
                    objGEXCELSh.cells(row, col) = cellContent   'paste in Excel
                        'objGEXCELSh.Columns(row, col).autofit
                Else
                    objGEXCELSh.cells(row, movedCol) = cellContent 'move every other column 3 steps to the right
                        'MsgBox cellContent
                        'objGEXCELSh.Columns(row, movedCol).autofit
                End If
                
            movedCol = movedCol + 2
        Next
    Next
    objGEXCELSh.Rows.autofit    'autofit rows
    objGEXCELSh.Columns.autofit
    objGEXCELSh.Columns.WrapText = True
   
    MsgBox "Table copied!"  'message of completion

End Sub

Sub StartEXCEL()    'function for opening excel
    Err.Clear
        On Error Resume Next    'error handling
            Set objGEXCELapp = GetObject(, "EXCEL.Application")     'start Excel

    If Err.Number <> 0 Then
        Err.Clear
            Set objGEXCELapp = CreateObject("EXCEL.Application")
    End If
'*****************************************************************************************************************
    objGEXCELapp.Application.Visible = True
        Set objGEXCELwkBks = objGEXCELapp.Application.WorkBooks     'prepare excel worksheets
        Set objGEXCELwkBk = objGEXCELwkBks.Add
        Set objGEXCELwkShs = objGEXCELwkBk.Worksheets(1)
        Set objGEXCELSh = objGEXCELwkBk.Sheets(1)
End Sub

Attribute VB_Name = "leaderForm"
Attribute VB_Base = "0{27043F48-9B16-4C0B-9DF5-5BC3C2A5AA05}{C2D88E69-9711-4A0D-A10A-2B2EE220EDDE}"
Attribute VB_GlobalNameSpace = False
Attribute VB_Creatable = False
Attribute VB_PredeclaredId = True
Attribute VB_Exposed = False
Attribute VB_TemplateDerived = False
Attribute VB_Customizable = False
'Macro created by Per Björk, Engineering Partner

Private Sub UserForm_Initialize()   'do this when form opens
    
    TBindexN.Text = 1
    
End Sub

Private Sub okBut_Click()
    
    indexL = TBindexL.Value
    indexN = TBindexN.Value
            
        If TBindexL.Value = "" Or IsNumeric(TBindexL.Value) = True Then
            MsgBox "Please input a index letter!", vbCritical, "Missing information!"
        
        Else
            Me.Hide
                TBindexL.Text = ""
                TBindexN.Text = ""
        End If
End Sub

Private Sub CancelBut_Click()
    TBindexL.Text = ""
    TBindexN.Text = ""
    
        Unload Me
End Sub

Private Sub UserForm_QueryClose(Cancel As Integer, CloseMode As Integer)    'together with cancel button terminates the whole macro
    End
End Sub

Attribute VB_Name = "mainForm"
Attribute VB_Base = "0{9E8E8462-4359-462E-8F19-BF65C70A936E}{70137211-CD1B-439D-8952-D437C0A4752F}"
Attribute VB_GlobalNameSpace = False
Attribute VB_Creatable = False
Attribute VB_PredeclaredId = True
Attribute VB_Exposed = False
Attribute VB_TemplateDerived = False
Attribute VB_Customizable = False
'Created by Per Björk, Engineering Partner

Private Sub UserForm_Initialize()   'do this when form opens
    Dim objName As String
        Dim winName As String
            Dim winCount As Integer         'count windows and display the names in drop down box
                winCount = CATIA.Windows.Count
    
    For i = 1 To winCount
        winName = CATIA.Windows.Item(i).Name
            catTargetDrwCbox.AddItem winName
    Next
    
        catTolCbox.AddItem "±1", 0    'catia tolerances
        catTolCbox.AddItem "±2", 1
        catTolCbox.AddItem "±3", 2
        catTolCbox.AddItem "±4", 3
        catTolCbox.AddItem "±5", 4
        catTolCbox.AddItem "±6", 5
        
            XLtolCbox.AddItem "±1", 0
            XLtolCbox.AddItem "±2", 1
            XLtolCbox.AddItem "±3", 2
            XLtolCbox.AddItem "±4", 3
            XLtolCbox.AddItem "±5", 4
            XLtolCbox.AddItem "±6", 5
    
    For s = 1 To Selection1.Count
        objName = Selection1.Item(s).Value.Name
            lbSelection.AddItem objName
    Next
End Sub

Private Sub UserForm_QueryClose(Cancel As Integer, CloseMode As Integer)    'together with cancel button terminates the whole macro
    End
End Sub

Private Sub catPolylineBut_Click()
    targetDrw = catTargetDrwCbox.Value
        headline = catHeadlineTbox.Value
            pointIndex = catPointIndexTbox.Value
                tol = catTolCbox.Value
        
    manX = manXtbox.Value
    manY = manYtbox.Value
    manZ = manZtbox.Value
        
        If catTargetDrwCbox.Value = "" Then    'user feedback controls
            MsgBox "Please select a target drawing!", vbCritical, "Missing information!"
        ElseIf catHeadlineTbox.Value = "" Then
            MsgBox "Please input a table headline!", vbCritical, "Missing information!"
        ElseIf catPointIndexTbox.Value = "" Then
            MsgBox "Please input a point index !", vbCritical, "Missing information!"
        Else
            Me.Hide
                'empty old values
                catTargetDrwCbox.Text = ""
                catHeadlineTbox.Text = ""
                catPointIndexTbox.Text = ""
                catTolCbox.Text = ""
                    manXtbox.Text = ""
                    manYtbox.Text = ""
                    manZtbox.Text = ""
                        lbSelection.Clear
            userChoice = 1
        End If
End Sub

Private Sub catInvPolylineBut_Click()
    targetDrw = catTargetDrwCbox.Value
        headline = catHeadlineTbox.Value
            pointIndex = catPointIndexTbox.Value
                tol = catTolCbox.Value
    
    manX = manXtbox.Value
    manY = manYtbox.Value
    manZ = manZtbox.Value
    
        If catTargetDrwCbox.Value = "" Then    'user feedback controls
            MsgBox "Please select a target drawing!", vbCritical, "Missing information!"
        ElseIf catHeadlineTbox.Value = "" Then
            MsgBox "Please input a table headline!", vbCritical, "Missing information!"
        ElseIf catPointIndexTbox.Value = "" Then
            MsgBox "Please input a point index !", vbCritical, "Missing information!"
        Else
            Me.Hide
                'empty old values
                catTargetDrwCbox.Text = ""
                catHeadlineTbox.Text = ""
                catPointIndexTbox.Text = ""
                catTolCbox.Text = ""
                    manXtbox.Text = ""
                    manYtbox.Text = ""
                    manZtbox.Text = ""
                        lbSelection.Clear
            userChoice = 2
        End If
End Sub

Private Sub catPointsBut_Click()
    targetDrw = catTargetDrwCbox.Value
        headline = catHeadlineTbox.Value
            pointIndex = catPointIndexTbox.Value
    
    manX = manXtbox.Value
    manY = manYtbox.Value
    manZ = manZtbox.Value
    
        If catTargetDrwCbox.Value = "" Then    'user feedback controls
            MsgBox "Please select a target drawing!", vbCritical, "Missing information!"
        ElseIf catHeadlineTbox.Value = "" Then
            MsgBox "Please input a table headline!", vbCritical, "Missing information!"
        ElseIf catPointIndexTbox.Value = "" Then
            MsgBox "Please input a point index!", vbCritical, "Missing information!"
        Else
            Me.Hide
                'empty old values
                catTargetDrwCbox.Text = ""
                catHeadlineTbox.Text = ""
                catPointIndexTbox.Text = ""
                catTolCbox.Text = ""
                    manXtbox.Text = ""
                    manYtbox.Text = ""
                    manZtbox.Text = ""
                        lbSelection.Clear
            userChoice = 3
        End If
End Sub

Private Sub catCancelBut_Click()    'closes the form
    Unload Me
        lbSelection.Clear
End Sub

Private Sub XLPolylineBut_Click()
    headline = XLheadlineTbox.Value
        pointIndex = XLpointIndexTbox.Value
            tol = XLtolCbox.Value
                    
    manX = manXtbox.Value
    manY = manYtbox.Value
    manZ = manZtbox.Value
                    
        If XLheadlineTbox.Value = "" Then
            MsgBox "Please input a table headline!", vbCritical, "Missing information!"
        ElseIf XLpointIndexTbox.Value = "" Then
            MsgBox "Please input a point index!", vbCritical, "Missing information!"
        Else
            Me.Hide
                'empty old values
                XLheadlineTbox.Text = ""
                XLpointIndexTbox.Text = ""
                XLtolCbox.Text = ""
                    manXtbox.Text = ""
                    manYtbox.Text = ""
                    manZtbox.Text = ""
                        lbSelection.Clear
            userChoice = 4
        End If
End Sub

Private Sub XLinvPolylineBut_Click()
    headline = XLheadlineTbox.Value
        pointIndex = XLpointIndexTbox.Value
            tol = XLtolCbox.Value
            
    manX = manXtbox.Value
    manY = manYtbox.Value
    manZ = manZtbox.Value
            
        If XLheadlineTbox.Value = "" Then
            MsgBox "Please input a table headline!", vbCritical, "Missing information!"
        ElseIf XLpointIndexTbox.Value = "" Then
            MsgBox "Please input a point index!", vbCritical, "Missing information!"
        Else
            Me.Hide
            'empty old values
            XLheadlineTbox.Text = ""
            XLpointIndexTbox.Text = ""
            XLtolCbox.Text = ""
                manXtbox.Text = ""
                manYtbox.Text = ""
                manZtbox.Text = ""
                    lbSelection.Clear
            userChoice = 5
        End If
End Sub

Private Sub XLpointsBut_Click()
    headline = XLheadlineTbox.Value
        pointIndex = XLpointIndexTbox.Value
            
    manX = manXtbox.Value
    manY = manYtbox.Value
    manZ = manZtbox.Value
            
        If XLheadlineTbox.Value = "" Then
            MsgBox "Please input a table headline!", vbCritical, "Missing information!"
        ElseIf XLpointIndexTbox.Value = "" Then
            MsgBox "Please input a point index!", vbCritical, "Missing information!"
        Else
            Me.Hide
            'empty old values
            XLheadlineTbox.Text = ""
            XLpointIndexTbox.Text = ""
            XLtolCbox.Text = ""
                manXtbox.Text = ""
                manYtbox.Text = ""
                manZtbox.Text = ""
                    lbSelection.Clear
            userChoice = 6
        End If
End Sub

Private Sub XLcancelBut_Click()
    Unload Me
        lbSelection.Clear
End Sub

Attribute VB_Name = "renameForm"
Attribute VB_Base = "0{9446EFB6-7B40-47E7-8E6E-BEAAC82CE6C4}{DBFC8C4F-9CA5-4582-96A5-D917A26C900D}"
Attribute VB_GlobalNameSpace = False
Attribute VB_Creatable = False
Attribute VB_PredeclaredId = True
Attribute VB_Exposed = False
Attribute VB_TemplateDerived = False
Attribute VB_Customizable = False
'Macro created by Per Björk, Engineering Partner

Private Sub UserForm_Initialize()   'do this when form opens
    Dim pointName As String
    For s = 1 To numberOfPoints
        pointName = selectedPoints.Item(s).Value.Name  'find the name for each point
            lbSelPoints.AddItem pointName       'add selection point name to list
    Next
    
End Sub

Private Sub okBut_Click()
    pointLetter = tbPointIndex.Value
        startNum = tbStartNum.Value
            
        If tbPointIndex.Value = "" Or IsNumeric(tbPointIndex.Value) = True Then     'user feedback messages
            MsgBox "Please input a index letter!", vbCritical, "Missing information!"
            
        Else
            tbPointIndex.Text = ""
            tbStartNum.Text = ""
            lbSelPoints.Clear
                Me.Hide
            
        End If
End Sub

Private Sub CancelBut_Click()
    Unload Me
End Sub

Private Sub UserForm_QueryClose(Cancel As Integer, CloseMode As Integer)    'together with cancel button terminates the whole macro
    End
End Sub

Attribute VB_Name = "tableMacro"
'****************************************************************************
'This macro creates drawing tables in Catia and Excel for selected polyline and points.
'X, Y, Z coordinates, radius for each point and total length of the polyline.

'Instructions for use:
'Select item(s) and run macro, select target drawing, input table headline and letter.
'Table with coordinates will be created in the view "TABLES" on selected drawing.

'Created by Per Björk, Engineering Partner 2014
'****************************************************************************

'variables
Dim Coords(2) As Variant
Dim TheMeasurable As Variant
Dim errorMes As Variant
Dim polyline1NrOfElements As Integer
Dim numberOfPoints As Integer
Dim foundTables As Boolean
Dim errorRep As Boolean

Dim objGEXCELapp As Object
Dim objGEXCELwkBks As Object
Dim objGEXCELwkBk As Object
Dim objGEXCELwkShs As Object
Dim objGEXCELSh As Object

Public Selection1 As Selection
Public targetDrw As String
Public headline As String
Public pointIndex As String
Public tol As String
Public userChoice As Integer

Public manX As Variant
Public manY As Variant
Public manZ As Variant

Sub CATMain()
On Error GoTo errorHandler  'errorhandlng
        
        Set Selection1 = CATIA.ActiveDocument.Selection 'handle the selection in catia
            If Selection1.Count = 0 Then    'if selection is empty display message
                MsgBox ("Nothing selected! Please select a polyline or at least one point.")
                    Exit Sub
            End If

                Load mainForm       'load main form
                    mainForm.Show
                    
                        If manX = "" Then
                            manX = 0
                        End If
                            
                            If manY = "" Then
                                manY = 0
                            End If
                        
                                If manZ = "" Then
                                    manZ = 0
                                End If
                    
                    If userChoice = 1 Or userChoice = 2 Then  'user choose to create a polyline table
                        catPolyline
                    ElseIf userChoice = 3 Then  'user choose to create a point table
                        catPoints
                    ElseIf userChoice = 4 Or userChoice = 5 Then
                        XLpolyline
                    ElseIf userChoice = 6 Then
                        XLpoints
                    End If

errorHandler:   'error messages
    If Err.Number = -2147467259 Then
        errorMes = MsgBox("No active 3D document!" & vbNewLine & "Load a 3D document and select a polyline or at least one point.", vbCritical, "Error!")
            Err.Number = 0
    End If
End Sub

Sub catPolyline()
On Error GoTo errorHandler  'errorhandlng
    
            'handle the selection in catia
            Set Selection1 = CATIA.ActiveDocument.Selection
                Set polyline1 = Selection1.Item(1)  'pick first element (the polyline) of the selection in Catia
                    If polyline1.Type <> "HybridShapePolyline" Then     'check if the object selected is a polyline
                        errorMes = MsgBox("Wrong type of object selected! Please select a polyline.", vbCritical, "Wrong type of object!!")
                        Exit Sub
                    End If
                    
                    Set myPolyline = polyline1.Value
                        polyline1NrOfElements = myPolyline.NumberOfElements  'count number of points in the polyline
'********************************************************************************************************************************
    'start table creation process
    CATIA.Windows.Item(targetDrw).Activate     'switch to drawing window
        Set myDoc = CATIA.ActiveDocument    'define active document and view
            Set mySheet = myDoc.Sheets.ActiveSheet
    
                For i = 1 To mySheet.Views.Count                'check if drawing view "TABLES" exists
                    Set myView = mySheet.Views.Item(i)      'set view
                        If myView.Name = "TABLES" Then             'if "TABLES" exists activate view and exit for-loop
                            Set myView = mySheet.Views.Item("TABLES")
                                myView.Activate
                                    foundTables = True
                                        Exit For
                        End If
                Next
        
                        If foundTables = False Then             'if "TABLES" doesn't exist, create it and activate
                            Set myView = mySheet.Views.Add("TABLES")
                                myView.Activate
                        End If

        'create the table itself
        Dim myTable As DrawingTable
        Set myTable = myView.Tables.Add(100, 100, polyline1NrOfElements + 3, 5, 7.5, 22)
    
            'add labels
            myTable.SetCellString 1, 1, headline
            myTable.SetCellString 2, 1, "POINT"
            myTable.SetCellString 2, 2, "X"
            myTable.SetCellString 2, 3, "Y"
            myTable.SetCellString 2, 4, "Z"
            myTable.SetCellString 2, 5, "RADIUS"
                'format the table
                myTable.MergeCells 1, 1, 1, 5
                    myTable.SetCellAlignment 1, 1, CatTableTopCenter
                myTable.MergeCells polyline1NrOfElements + 3, 1, 1, 5
                    myTable.SetCellAlignment polyline1NrOfElements + 3, 1, CatTableTopCenter
'**************************************************************************************************************************************
    'coordinate extraction process
    Dim TheSPAWorkbench As Workbench
    Set TheSPAWorkbench = CATIA.ActiveDocument.GetWorkbench("SPAWorkbench") ' set TheSPAWorkbench
        Dim pointRef As Reference
            Dim oRad As Length
'**************************************************************************************************************************************
            If userChoice = 1 Then  'normal polyline
                For i = 1 To polyline1NrOfElements       'iterate through all poinst of polyline
                    myPolyline.GetElement i, pointRef, oRad
                            
                    'set refObject
                    Set TheMeasurable = TheSPAWorkbench.GetMeasurable(pointRef)             ' set Measurable with reference
                        TheMeasurable.GetPoint Coords                                           ' get coordinates from Measurable
                    Set MeasureLength = TheSPAWorkbench.GetMeasurable(myPolyline)
                        myPolylineLength = MeasureLength.Length
                        
                    If oRad Is Nothing Then RadiusAtPoint = False Else: RadiusAtPoint = True                ' check if Radius at point
                                       
                    'add point index
                    myTable.SetCellString 2 + i, 1, pointIndex & i
                    
                    xPoint = Coords(0)
                    Coords(0) = xPoint + manX
                    xPoint = Round(Coords(0), 1) 'check decimals
                        If xPoint = 0 Then      'avoid division with zero
                            myTable.SetCellString 2 + i, 2, "0,0"       'add "0,0"
                        ElseIf Int(xPoint) / xPoint = 1 Then        'check if integer
                            myTable.SetCellString 2 + i, 2, xPoint & ",0"       'add ",0"
                        Else
                            myTable.SetCellString 2 + i, 2, Round(Coords(0), 1)    'else, use 1 decimal
                        End If
                    
                    yPoint = Coords(1)
                    Coords(1) = yPoint + manY
                    yPoint = Round(Coords(1), 1)       'same procedure for y and z
                        If yPoint = 0 Then
                            myTable.SetCellString 2 + i, 3, "0,0"
                        ElseIf Int(yPoint) / yPoint = 1 Then
                            myTable.SetCellString 2 + i, 3, yPoint & ",0"
                        Else
                            myTable.SetCellString 2 + i, 3, Round(Coords(1), 1)
                        End If
        
                    zPoint = Coords(2)
                    Coords(2) = zPoint + manZ
                    zPoint = Round(Coords(2), 1)
                        If zPoint = 0 Then
                            myTable.SetCellString 2 + i, 4, "0,0"
                        ElseIf Int(zPoint) / zPoint = 1 Then
                            myTable.SetCellString 2 + i, 4, zPoint & ",0"
                        Else
                            myTable.SetCellString 2 + i, 4, Round(Coords(2), 1)
                        End If
                                        
                    If RadiusAtPoint Then
                        radPoint = Round(oRad.Value, 1)     'same method as above
                            If radPoint = 0 Then
                                myTable.SetCellString 2 + i, 5, ""
                            ElseIf Int(radPoint) / radPoint = 1 Then
                                myTable.SetCellString 2 + i, 5, radPoint & ",0"
                            Else
                                myTable.SetCellString 2 + i, 5, Round(oRad.Value, 1)
                            End If
                    End If
                Next
 '**************************************************************************************************************************************************
            ElseIf userChoice = 2 Then  'inverted polyline
                x = 1
                For i = polyline1NrOfElements To 1 Step -1        'iterate through all poinst of polyline
                    myPolyline.GetElement i, pointRef, oRad
                            
                    'set refObject
                    Set TheMeasurable = TheSPAWorkbench.GetMeasurable(pointRef)             ' set Measurable with reference
                        TheMeasurable.GetPoint Coords                                           ' get coordinates from Measurable
                    Set MeasureLength = TheSPAWorkbench.GetMeasurable(myPolyline)
                        myPolylineLength = MeasureLength.Length
                        
                    If oRad Is Nothing Then RadiusAtPoint = False Else: RadiusAtPoint = True                ' check if Radius at point
                    
                    myTable.SetCellString 2 + x, 1, pointIndex & x  'set point ref
            
                        xPoint = Coords(0)
                        Coords(0) = xPoint + manX
                        xPoint = Round(Coords(0), 1) 'check decimals
                            If xPoint = 0 Then      'avoid division with zero
                                myTable.SetCellString (2 + i) - (i - x), 2, "0,0" 'add "0,0"
                            ElseIf Int(xPoint) / xPoint = 1 Then        'check if integer
                                myTable.SetCellString (2 + i) - (i - x), 2, xPoint & ",0"      'add ",0"
                            Else
                                myTable.SetCellString (2 + i) - (i - x), 2, Round(Coords(0), 1)     'else, use 1 decimal
                            End If
                        
                        yPoint = Coords(1)
                        Coords(1) = yPoint + manY
                        yPoint = Round(Coords(1), 1)        'same procedure for y and z
                            If yPoint = 0 Then
                                myTable.SetCellString (2 + i) - (i - x), 3, "0,0"
                            ElseIf Int(yPoint) / yPoint = 1 Then
                                myTable.SetCellString (2 + i) - (i - x), 3, yPoint & ",0"
                            Else
                                myTable.SetCellString (2 + i) - (i - x), 3, Round(Coords(1), 1)
                            End If
            
                        zPoint = Coords(2)
                        Coords(2) = zPoint + manZ
                        zPoint = Round(Coords(2), 1)
                            If zPoint = 0 Then
                                myTable.SetCellString (2 + i) - (i - x), 4, "0,0"
                            ElseIf Int(zPoint) / zPoint = 1 Then
                                myTable.SetCellString (2 + i) - (i - x), 4, zPoint & ",0"
                            Else
                                myTable.SetCellString (2 + i) - (i - x), 4, Round(Coords(2), 1)
                            End If
                                            
                        If RadiusAtPoint Then
                            radPoint = Round(oRad.Value, 1)     'same method as above
                                If radPoint = 0 Then
                                    myTable.SetCellString (2 + i) - (i - x), 5, ""
                                ElseIf Int(radPoint) / radPoint = 1 Then
                                    myTable.SetCellString (2 + i) - (i - x), 5, radPoint & ",0"
                                Else
                                    myTable.SetCellString (2 + i) - (i - x), 5, Round(oRad.Value, 1)
                                End If
                        End If
                        
                    x = x + 1   'add 1 to x for every turn of the loop
                Next
            End If
'****************************************************************************************************************************************
                polyLength = Round(myPolylineLength, 1)  'add length, check integer, same method as above
                    If Int(polyLength) / polyLength = 1 Then
                        myTable.SetCellString polyline1NrOfElements + 3, 1, "TOTAL LENGTH = " & polyLength & ",0" & tol & " MM"
                    Else
                        myTable.SetCellString polyline1NrOfElements + 3, 1, "TOTAL LENGTH = " & Round(myPolylineLength, 1) & tol & " MM"
                    End If
                    
                MsgBox "Polyline coordinate table created!"  'display message of completion
'***************************************************************************************************************************************************
errorHandler:   'error messages
    If Err.Number = 438 Then
        errorMes = MsgBox("Can't create drawing table in a 3D document! Please select window containing the target drawing.", vbCritical, "Error!")
            Err.Number = 0
                Exit Sub
    ElseIf Err.Number = -2147467259 Then
        errorMes = MsgBox("Wrong type of object(s) selected! This function only works with point items.", vbCritical, "Error!")
            Err.Number = 0
    End If
End Sub

Sub catPoints()
On Error GoTo errorHandler  'set up errorhandler

    Dim Selection1 As Selection 'handle selection
    Set Selection1 = CATIA.ActiveDocument.Selection
        numberOfPoints = Selection1.Count
    
    'start table creation process
    CATIA.Windows.Item(targetDrw).Activate     'switch to drawing window
        Set myDoc = CATIA.ActiveDocument    'define active document and view
            Set mySheet = myDoc.Sheets.ActiveSheet
            
    For i = 1 To mySheet.Views.Count                'check if drawing view "TABLES" exists
        Set myView = mySheet.Views.Item(i)      'set view
            If myView.Name = "TABLES" Then             'if "TABLES" exists activate view and exit for loop
                Set myView = mySheet.Views.Item("TABLES")
                    myView.Activate
                        foundTables = True
                            Exit For
            End If
    Next
        
            If foundTables = False Then             'if "TABLES" doesn't exist, create and activate it
                Set myView = mySheet.Views.Add("TABLES")
                    myView.Activate
            End If
        
        'create the table itself
        Dim myTable As DrawingTable
        Set myTable = myView.Tables.Add(100, 100, numberOfPoints + 2, 4, 7.5, 23)
        'add labels
        myTable.SetCellString 1, 1, headline
        myTable.SetCellString 2, 1, "POINT"
        myTable.SetCellString 2, 2, "X"
        myTable.SetCellString 2, 3, "Y"
        myTable.SetCellString 2, 4, "Z"
        myTable.MergeCells 1, 1, 1, 4
        myTable.SetCellAlignment 1, 1, CatTableTopCenter
        
'**********************************************************************************************************************************************
    'coordinate extraction process
    Dim TheSPAWorkbench As Workbench
    Set TheSPAWorkbench = CATIA.ActiveDocument.GetWorkbench("SPAWorkbench") ' set TheSPAWorkbench
        Dim pointRef As Reference
            Dim oRad As Length
'**********************************************************************************************************************************************
    For i = 1 To numberOfPoints                 'create correct number of rows
        Set Element = Selection1.Item(i)
            Set selPoint = Element.Value
        
        Set TheMeasurable = TheSPAWorkbench.GetMeasurable(selPoint)
            TheMeasurable.GetPoint Coords       'get coordinates from Measurable
                
            myTable.SetCellString 2 + i, 1, pointIndex & i  'add point index

                xPoint = Coords(0)
                Coords(0) = xPoint + manX
                xPoint = Round(Coords(0), 1) 'check decimals
                    If xPoint = 0 Then  'avoid division with zero
                        myTable.SetCellString 2 + i, 2, "0,0"   'add 0,0
                    ElseIf Int(xPoint) / xPoint = 1 Then        'if integer
                        myTable.SetCellString 2 + i, 2, xPoint & ",0"       'add ",0"
                    Else
                        myTable.SetCellString 2 + i, 2, Round(Coords(0), 1)     'else, use 1 decimal
                    End If
                
                yPoint = Coords(1)
                Coords(1) = yPoint + manY
                yPoint = Round(Coords(1), 1)        'same procedure for y and z
                    If yPoint = 0 Then
                        myTable.SetCellString 2 + i, 3, "0,0"
                    ElseIf Int(yPoint) / yPoint = 1 Then
                        myTable.SetCellString 2 + i, 3, yPoint & ",0"
                    Else
                        myTable.SetCellString 2 + i, 3, Round(Coords(1), 1)
                    End If

                zPoint = Coords(2)
                Coords(2) = zPoint + manZ
                zPoint = Round(Coords(2), 1)
                    If zPoint = 0 Then
                        myTable.SetCellString 2 + i, 4, "0,0"
                    ElseIf Int(zPoint) / zPoint = 1 Then
                        myTable.SetCellString 2 + i, 4, zPoint & ",0"
                    Else
                        myTable.SetCellString 2 + i, 4, Round(Coords(2), 1)
                    End If
        Next
        
        MsgBox "Point coordinate table created!" & vbNewLine & "Points are presented in order of selection."  'display message of completion
'***************************************************************************************************************************************************
errorHandler:   'error messages
    If Err.Number = 438 Then
        errorMes = MsgBox("Can't create drawing table in a 3D document! Please select window containing the target drawing.", vbCritical, "Error")
            Err.Number = 0
    ElseIf Err.Number = -2147467259 Then
        errorMes = MsgBox("Wrong type of object(s) selected! This function only works with point items.", vbCritical, "Error!")
            Err.Number = 0
    End If
End Sub

Sub XLpolyline()
On Error GoTo errorHandler
    
        'handle the selection in catia
        Set Selection1 = CATIA.ActiveDocument.Selection
            Set polyline1 = Selection1.Item(1)  'pick first element (the polyline) of the selection in Catia
                If polyline1.Type <> "HybridShapePolyline" Then     'check if the object selected is a polyline
                        errorMes = MsgBox("Wrong type of object selected! Please select a polyline.", vbCritical, "Wrong type of object!!")
                    Exit Sub
                End If
            Set myPolyline = polyline1.Value
                polyline1NrOfElements = myPolyline.NumberOfElements  'count number of points in the polyline
'************************************************************************************************************************************************
        StartEXCEL  'run Excel
        
        Dim TheSPAWorkbench As Workbench
        Set TheSPAWorkbench = CATIA.ActiveDocument.GetWorkbench("SPAWorkbench") 'set TheSPAWorkbench
            Dim pointRef As Reference
                Dim oRad  As Length
'************************************************************************************************************************************************
    If userChoice = 4 Then    'normal polyline
        For i = 1 To polyline1NrOfElements  'iterate through all poinst of polyline
            myPolyline.GetElement i, pointRef, oRad
                
                Set TheMeasurable = TheSPAWorkbench.GetMeasurable(pointRef)
                    TheMeasurable.GetPoint Coords                                           'get coordinates from Measurable
                Set MeasureLength = TheSPAWorkbench.GetMeasurable(myPolyline)
                    myPolylineLength = MeasureLength.Length

            If oRad Is Nothing Then RadiusAtPoint = False Else RadiusAtPoint = True ' check if Radius at point
             
            'write data to Excel sheet
            objGEXCELSh.cells(i + 2, "A") = pointIndex & i      'add point name

            xPoint = Coords(0)
            Coords(0) = xPoint + manX
            xPoint = Round(Coords(0), 1) 'check decimals
                If xPoint = 0 Then      'prevent divison by zero
                    objGEXCELSh.cells(i + 2, "C") = "0,0"       'add "0,0"
                ElseIf Int(xPoint) / xPoint = 1 Then        'check if integer
                    objGEXCELSh.cells(i + 2, "C") = xPoint & ",0"       'add ",0"
                Else
                    objGEXCELSh.cells(i + 2, "C") = Round(Coords(0), 1) 'else, use 1 decimal
                End If
                
            yPoint = Coords(1)
            Coords(1) = yPoint + manY
            yPoint = Round(Coords(1), 1)        'same procedure for y and z
                If yPoint = 0 Then
                    objGEXCELSh.cells(i + 2, "E") = "0,0"
                ElseIf Int(yPoint) / yPoint = 1 Then
                    objGEXCELSh.cells(i + 2, "E") = yPoint & ",0"
                Else
                    objGEXCELSh.cells(i + 2, "E") = Round(Coords(1), 1)
                End If
    
            zPoint = Coords(2)
            Coords(2) = zPoint + manZ
            zPoint = Round(Coords(2), 1)
                If zPoint = 0 Then
                    objGEXCELSh.cells(i + 2, "G") = "0,0"
                ElseIf Int(zPoint) / zPoint = 1 Then
                    objGEXCELSh.cells(i + 2, "G") = zPoint & ",0"
                Else
                    objGEXCELSh.cells(i + 2, "G") = Round(Coords(2), 1)
                End If
                
                    If RadiusAtPoint Then   'add radius value
                        radPoint = Round(oRad.Value, 1)     'same method as above
                            If radPoint = 0 Then
                                objGEXCELSh.cells(i + 2, "I") = ""
                            ElseIf Int(radPoint) / radPoint = 1 Then
                                objGEXCELSh.cells(i + 2, "I") = radPoint & ",0"
                            Else
                                objGEXCELSh.cells(i + 2, "I") = Round(oRad.Value, 1)
                            End If
                    End If
        Next
        
    ElseIf userChoice = 5 Then    'inverted polyline
        x = 1
        For i = polyline1NrOfElements To 1 Step -1  'iterate through all poinst of polyline
            
                myPolyline.GetElement i, pointRef, oRad
                    
                    Set TheMeasurable = TheSPAWorkbench.GetMeasurable(pointRef)
                        TheMeasurable.GetPoint Coords                       'get coordinates from Measurable
                    Set MeasureLength = TheSPAWorkbench.GetMeasurable(myPolyline)
                        myPolylineLength = MeasureLength.Length
    
                If oRad Is Nothing Then RadiusAtPoint = False Else RadiusAtPoint = True ' check if Radius at point
                 
                'write data to Excel sheet
                objGEXCELSh.cells(x + 2, "A") = pointIndex & x      'add point name
    
            xPoint = Coords(0)
            Coords(0) = xPoint + manX
            xPoint = Round(Coords(0), 1) 'check decimals
                If xPoint = 0 Then      'prevent divison by zero
                    objGEXCELSh.cells((2 + i) - (i - x), "C") = "0,0"       'add "0,0"  (2 + i) - (i - X), 2, "0,0" 'add "0,0"
                ElseIf Int(xPoint) / xPoint = 1 Then        'check if integer
                    objGEXCELSh.cells((2 + i) - (i - x), "C") = xPoint & ",0"       'add ",0"
                Else
                    objGEXCELSh.cells((2 + i) - (i - x), "C") = Round(Coords(0), 1) 'else, use 1 decimal
                End If
                
            yPoint = Coords(1)
            Coords(1) = yPoint + manY
            yPoint = Round(Coords(1), 1)        'same procedure for y and z
                If yPoint = 0 Then
                    objGEXCELSh.cells((2 + i) - (i - x), "E") = "0,0"
                ElseIf Int(yPoint) / yPoint = 1 Then
                    objGEXCELSh.cells((2 + i) - (i - x), "E") = yPoint & ",0"
                Else
                    objGEXCELSh.cells((2 + i) - (i - x), "E") = Round(Coords(1), 1)
                End If
    
            zPoint = Coords(2)
            Coords(2) = zPoint + manZ
            zPoint = Round(Coords(2), 1)
                If zPoint = 0 Then
                    objGEXCELSh.cells((2 + i) - (i - x), "G") = "0,0"
                ElseIf Int(zPoint) / zPoint = 1 Then
                    objGEXCELSh.cells((2 + i) - (i - x), "G") = zPoint & ",0"
                Else
                    objGEXCELSh.cells((2 + i) - (i - x), "G") = Round(Coords(2), 1)
                End If
                
                    If RadiusAtPoint Then   'add radius value
                        radPoint = Round(oRad.Value, 1)     'same method as above
                            If radPoint = 0 Then
                                objGEXCELSh.cells((2 + i) - (i - x), "I") = ""
                            ElseIf Int(radPoint) / radPoint = 1 Then
                                objGEXCELSh.cells((2 + i) - (i - x), "I") = radPoint & ",0"
                            Else
                                objGEXCELSh.cells((2 + i) - (i - x), "I") = Round(oRad.Value, 1)
                            End If
                    End If
         
        x = x + 1   'add 1 to x for every turn of the loop
        Next
    End If
'**********************************************************************************************************************************************************
                polyLength = Round(myPolylineLength, 1)  'add length, check integer, same method as aboove
                        If Int(polyLength) / polyLength = 1 Then
                            objGEXCELSh.cells(polyline1NrOfElements + 3, "D") = "TOTAL LENGTH = " & polyLength & ",0" & tol & " MM"
                        Else
                            objGEXCELSh.cells(polyline1NrOfElements + 3, "D") = "TOTAL LENGTH = " & Round(myPolylineLength, 1) & tol & " MM"    'the length
                        End If
                
                MsgBox "Coordinate extraction complete!"       'completion message
'**********************************************************************************************************************************************************
errorHandler:   'error messages
    If Err.Number = -2147467259 Then
        errorMes = MsgBox("Wrong type of object(s) selected! This function only works with point items.", vbCritical, "Error!")
            Err.Number = 0
    End If
End Sub

Sub XLpoints()
    On Error GoTo errorHandler  'errorhandler
    
    'set up selection
    Set Selection1 = CATIA.ActiveDocument.Selection
        numberOfPoints = Selection1.Count
'*******************************************************************************************************************
    StartEXCEL
'*******************************************************************************************************************
    Dim TheSPAWorkbench As Workbench
    Set TheSPAWorkbench = CATIA.ActiveDocument.GetWorkbench("SPAWorkbench")     'set TheSPAWorkbench
        Dim pointRef As Reference
            Dim oRad As Length
'*******************************************************************************************************************
    For i = 1 To Selection1.Count       'go through the selected points
        Set Element = Selection1.Item(i)
            Set selPoint = Element.Value
        
            Set TheMeasurable = TheSPAWorkbench.GetMeasurable(selPoint)
                TheMeasurable.GetPoint Coords              'get coordinates from Measurable

        objGEXCELSh.cells(i + 2, "A") = pointIndex & i  'add point prefix
        
        xPoint = Coords(1)
        Coords(1) = xPoint + manX
        xPoint = Round(Coords(1), 1)        'same procedure for y and z
            If xPoint = 0 Then      'prevent division by zero
                objGEXCELSh.cells(i + 2, "C") = "0,0"       'add "0,0"
            ElseIf Int(xPoint) / xPoint = 1 Then        'check if integer
                objGEXCELSh.cells(i + 2, "C") = xPoint & ",0"       'add ",0"
            Else
                objGEXCELSh.cells(i + 2, "C") = Round(Coords(0), 1) 'else, use 1 decimal
            End If
            
        yPoint = Coords(2)
        Coords(2) = yPoint + manY
        yPoint = Round(Coords(2), 1)
            If yPoint = 0 Then
                objGEXCELSh.cells(i + 2, "E") = "0,0"
            ElseIf Int(yPoint) / yPoint = 1 Then
                objGEXCELSh.cells(i + 2, "E") = yPoint & ",0"
            Else
                objGEXCELSh.cells(i + 2, "E") = Round(Coords(1), 1)
            End If

        zPoint = Coords(2)
        Coords(2) = zPoint + manZ
        zPoint = Round(Coords(2), 1)
            If zPoint = 0 Then
                objGEXCELSh.cells(i + 2, "G") = "0,0"
            ElseIf Int(zPoint) / zPoint = 1 Then
                objGEXCELSh.cells(i + 2, "G") = zPoint & ",0"
            Else
                objGEXCELSh.cells(i + 2, "G") = Round(Coords(2), 1)
            End If
    Next
            MsgBox "Coordinate extraction complete!" & vbNewLine & "Points are presented in order of selection."    'display completion message
'**************************************************************************************************************************************************
errorHandler:   'error message
    If Err.Number = -2147467259 Then
        errorMes = MsgBox("Wrong type of object(s) selected! This function only works with point items.", vbCritical, "Error!")
            Err.Number = 0
    End If
    
End Sub

Sub StartEXCEL()    'function for opening excel
    Err.Clear
        On Error Resume Next    'error handling
            Set objGEXCELapp = GetObject(, "EXCEL.Application")     'start Excel

    If Err.Number <> 0 Then
        Err.Clear
            Set objGEXCELapp = CreateObject("EXCEL.Application")
    End If
'*****************************************************************************************************************
    objGEXCELapp.Application.Visible = True
        Set objGEXCELwkBks = objGEXCELapp.Application.WorkBooks     'prepare excel worksheets
        Set objGEXCELwkBk = objGEXCELwkBks.Add
        Set objGEXCELwkShs = objGEXCELwkBk.Worksheets(1)
        Set objGEXCELSh = objGEXCELwkBk.Sheets(1)
            objGEXCELSh.cells(1, "D") = headline         'add table headlines
            objGEXCELSh.cells(2, "A") = "POINT"
            objGEXCELSh.cells(2, "C") = "X"
            objGEXCELSh.cells(2, "E") = "Y"
            objGEXCELSh.cells(2, "G") = "Z"
            If userChoice <> 6 Then
                objGEXCELSh.cells(2, "I") = "RADIUS"    'add only "RADIUS" for polylines
            End If
End Sub
