Attribute VB_Name = "Leaders3DPMI"
'Macro created by Per Björk, Engineering Partner
'This macro creates text labels with leaders for selected 3D points in 3DPMI documents.

'Variables
Public ParentHB As HybridBody
Public CompGeom
Public part1 As Part
Public targetPart As String
Public letterL As String
Public numberL As String
Public parentName As String

Dim objPart As Part
Dim pointName As String
Dim pointType As String
Dim partName As String
Dim oPartName As String
Dim nPartName As String
Dim numberOfPoints As Integer
Dim Coords(2) As Variant

Sub CATMain()
    On Error GoTo errorHandler:
        
        Dim selection1 As Selection
        Set selection1 = CATIA.ActiveDocument.Selection 'handle the selection in catia
            numberOfPoints = selection1.Count
                If numberOfPoints = 0 Then    'if selection is empty display message
                    MsgBox "Nothing selected! Please select at least one point.", vbCritical, "Empty selection!"
                        Exit Sub
                End If
        
        leaderForm.Show     'show form

'**********************************************************************************************************************************************
    'start coordinate extraction process
    Dim TheSPAWorkbench As Workbench
    Set TheSPAWorkbench = CATIA.ActiveDocument.GetWorkbench("SPAWorkbench")     'set TheSPAWorkbench
'**********************************************************************************************************************************************
    For i = 1 To numberOfPoints                 'create correct number of rows
        Set Element = selection1.Item(i)
            pointName = Element.Value.Name
                pointType = Element.Type
        
        Set objPart = GetPartFromObject(Element.Value)
                
            Set TheMeasurable = TheSPAWorkbench.GetMeasurable(Element.Value)
                TheMeasurable.GetPoint Coords       'get coordinates from Measurable
    
                    xPoint = Coords(0)  'store the x, y, and z coordinates
                    yPoint = Coords(1)
                    zPoint = Coords(2)
                                    
                    oPartName = objPart.Name      'get the partname
                    nPartName = Left(oPartName, Len(oPartName) - 2) & ".CATPart"      'remove last two characters and add ".CATPart" to the end
                    
                    Dim documents1 As Documents     'all the iterations for Catia to reach down into the feature tree
                    Set documents1 = CATIA.Documents
                
                    Dim partDocument1 As PartDocument
                    Set partDocument1 = documents1.Item(nPartName)
                    
                    Set part1 = partDocument1.Part
                
                    Dim annotationSets1 As AnnotationSets
                    Set annotationSets1 = part1.AnnotationSets
                
                    Dim annotationSet1 As AnnotationSet
                    Set annotationSet1 = annotationSets1.Add("VCS_ISO_3D_ASSY")
                
                If pointType = "HybridShapePointExplicit" Then  'dead points ****************************************

                    Dim parameters1 As Parameters
                    Set parameters1 = part1.Parameters

                    Dim HybridShapePointExplicit1 As HybridShapePointExplicit
                    Set HybridShapePointExplicit1 = parameters1.Item(pointName)

                    Dim reference1 As Reference
                    Set reference1 = part1.CreateReferenceFromObject(HybridShapePointExplicit1)
                    
                    Dim userSurfaces1 As UserSurfaces
                    Set userSurfaces1 = part1.UserSurfaces

                    Dim userSurface1 As UserSurface     'set up target surface for each point
                    Set userSurface1 = userSurfaces1.Generate(reference1)

                    Dim annotationFactory1 As AnnotationFactory     'set up annotations
                    Set annotationFactory1 = annotationSet1.AnnotationFactory

                    Dim annotation1 As Annotation
                    Set annotation1 = annotationFactory1.CreateEvoluateText(userSurface1, xPoint + 60, yPoint + 30, zPoint, True)   'create the  annotation

                    annotation1.Text.Text = letterL & numberL   'add index and number
                    annotation1.Text.Get2dAnnot.Leaders.Item(1).HeadSymbol = catFilledArrow  'define the leader headsymbol, a filled arrow

                ElseIf pointType = "HybridShapePointCoord" Then     'living points *******************************
                                            
                    getHybridParent Element.Value
                    
                    Dim hybridShapes1 As HybridShapes
                    Set hybridShapes1 = ParentHB.HybridShapes

                    Dim HybridShapePointCoord1 As HybridShapePointCoord
                    Set HybridShapePointCoord1 = hybridShapes1.Item(pointName)

                    Dim reference2 As Reference
                    Set reference2 = part1.CreateReferenceFromObject(HybridShapePointCoord1)

                    Dim userSurfaces2 As UserSurfaces
                    Set userSurfaces2 = part1.UserSurfaces

                    Dim userSurface2 As UserSurface     'set up target surface for each point
                    Set userSurface2 = userSurfaces2.Generate(reference2)

                    Dim annotationFactory2 As AnnotationFactory     'set up annotations
                    Set annotationFactory2 = annotationSet1.AnnotationFactory

                    Dim annotation2 As Annotation
                    Set annotation2 = annotationFactory2.CreateEvoluateText(userSurface2, xPoint + 60, yPoint + 30, zPoint, True)   'create the  annotation

                    annotation2.Text.Text = letterL & numberL   'add index and number
                    annotation2.Text.Get2dAnnot.Leaders.Item(1).HeadSymbol = catFilledArrow  'define the leader headsymbol, a filled arrow

                ElseIf pointType = "HybridShapeProject" Then        'projects *************************************
                    
                    getHybridParent Element.Value
                    
                    Dim hybridShapes2 As HybridShapes
                    Set hybridShapes2 = ParentHB.HybridShapes

                    Dim hybridShapeProject1 As HybridShapeProject
                    Set hybridShapeProject1 = hybridShapes2.Item(pointName)

                    Dim reference3 As Reference
                    Set reference3 = part1.CreateReferenceFromObject(hybridShapeProject1)

                    Dim userSurfaces3 As UserSurfaces
                    Set userSurfaces3 = part1.UserSurfaces

                    Dim userSurface3 As UserSurface     'set up target surface for each point
                    Set userSurface3 = userSurfaces3.Generate(reference3)

                    Dim annotationFactory3 As AnnotationFactory     'set up annotations
                    Set annotationFactory3 = annotationSet1.AnnotationFactory

                    Dim annotation3 As Annotation
                    Set annotation3 = annotationFactory3.CreateEvoluateText(userSurface3, xPoint + 60, yPoint + 30, zPoint, True)   'create the  annotation

                    annotation3.Text.Text = letterL & numberL   'add index and number
                    annotation3.Text.Get2dAnnot.Leaders.Item(1).HeadSymbol = catFilledArrow  'define the leader headsymbol, a filled arrow

                ElseIf pointType = "HybridShapeTranslate" Then      'translates ********************************
                    
                    getHybridParent Element.Value
                    
                    Dim hybridShapes3 As HybridShapes
                    Set hybridShapes3 = ParentHB.HybridShapes

                    Dim hybridShapeTranslate1 As HybridShapeTranslate
                    Set hybridShapeTranslate1 = hybridShapes3.Item(pointName)

                    Dim reference4 As Reference
                    Set reference4 = part1.CreateReferenceFromObject(hybridShapeTranslate1)

                    Dim userSurfaces4 As UserSurfaces
                    Set userSurfaces4 = part1.UserSurfaces

                    Dim userSurface4 As UserSurface     'set up target surface for each point
                    Set userSurface4 = userSurfaces4.Generate(reference4)

                    Dim annotationFactory4 As AnnotationFactory     'set up annotations
                    Set annotationFactory4 = annotationSet1.AnnotationFactory

                    Dim annotation4 As Annotation
                    Set annotation4 = annotationFactory4.CreateEvoluateText(userSurface4, xPoint + 60, yPoint + 30, zPoint, True)   'create the  annotation

                    annotation4.Text.Text = letterL & numberL   'add index and number
                    annotation4.Text.Get2dAnnot.Leaders.Item(1).HeadSymbol = catFilledArrow  'define the leader headsymbol, a filled arrow
                
                End If
                   
                    numberL = numberL + 1      'increase the number with one
    Next
            part1.Update    'update the part document
            
        MsgBox "Leaders created!" & vbNewLine & "Leaders are added to the points in order of selection."  'display message of completion
'***************************************************************************************************************************************************
errorHandler:           'error messages
'    MsgBox "The most recent error number is " & Err & _
'          ". Its message text is: " & Error(Err)

    If Err.Number = -2147467259 Then
        errorMes = MsgBox("You have to select points from the feature tree.", vbCritical, "Error!")
            Err.Number = 0
    End If
End Sub

Function GetPartFromObject(ByRef iObject As Object) As Part
    'This function calls itself recursively to access the
    'parent of the object passed in until a Part object
    'is reached.
    Dim strType As String
        'Get the type of the object passed into the function
        strType = TypeName(iObject)
            If strType = "Part" Then
                'If the object passed in is a part, return it and exit
                Set GetPartFromObject = iObject
                    Exit Function
            ElseIf strType = TypeName(iObject.Parent) Then
                'If the type of this object is the same as the parent object
                'then return nothing. The reason is the Parent property of
                'some objects simply returns the same object. This will never
                'get us to the part and will result in an infinite loop.
                'Example object types are Reference and Resource among others
                Set GetPartFromObject = Nothing
                    Exit Function
            Else
                'Call the function again and pass it the object’s parent
                Set GetPartFromObject = GetPartFromObject(iObject.Parent)
            End If
End Function

Function getHybridParent(InputGeom As HybridShape) As HybridBody
    Dim CurHBs As HybridBodies
    Set CurHBs = part1.HybridBodies
        Set CompGeom = InputGeom
            For v = 1 To CurHBs.Count
                RecHB CurHBs.Item(v)
                    If Not ParentHB Is Nothing Then
                        Set getHybridParent = ParentHB
                            Exit Function
                    End If
            Next v
End Function

Sub RecHB(inputHb As HybridBody)
    If inputHb.HybridBodies.Count <> 0 And Not CompGeom Is Nothing Then
         For xx = 1 To inputHb.HybridBodies.Count       'first level
             For yy = 1 To inputHb.HybridBodies.Item(xx).HybridBodies.Count     'second level
                If inputHb.HybridBodies.Item(xx).HybridBodies.Item(yy).Name = CompGeom.Name Then
                    Set ParentHB = inputHb.HybridBodies.Item(xx)
                        Set CompGeom = Nothing
                        Exit Sub
                End If

                If CompGeom Is Nothing Then
                    Exit Sub
                End If
            Next yy

            For yy = 1 To inputHb.HybridBodies.Item(xx).HybridShapes.Count  'next level
                If inputHb.HybridBodies.Item(xx).HybridShapes.Item(yy).Name = CompGeom.Name Then
                    Set ParentHB = inputHb.HybridBodies.Item(xx)
                        Set CompGeom = Nothing
                            Exit Sub
                End If

                If CompGeom Is Nothing Then
                    Exit Sub
                End If
            Next yy

            RecHB inputHb.HybridBodies.Item(xx)     'call the function again
            If CompGeom Is Nothing Then
                Exit Sub
            End If
        Next xx
    End If
End Sub

Attribute VB_Name = "getItemInfo"

'**********************************************************************************************************
'This macro gives the object name and type.

'Instructions for use:
'Select one or more objects and run macro.
'Macro will count number of items in selection and return name and type for each object.
'**********************************************************************************************************
'Created by Per Björk, Engineering partner 2014

'variables
Dim errorMes As Variant
Dim oSel As Selection

Sub CATMain()
On Error GoTo errorHandler  'errorhandlng
    
        Set oSel = CATIA.ActiveDocument.Selection
            If oSel.Count = 0 Then
                MsgBox "Nothing selected!" & vbNewLine & "Select an object."        'give errormessage if selection is empty
            End If
            
        MsgBox ("Number of objects selected: " & oSel.Count)    'list number of objects selected
            For i = 1 To oSel.Count     'go through selection of objects
                Set selEl = oSel.Item(i)
                    MsgBox ("Item name: " & selEl.Value.Name & vbNewLine & "Item type: " & selEl.Type)  'list name and type
            Next
                oSel.Clear      'clear selection
            
            
errorHandler:   'error messages
    If Err.Number = -2147467259 Then
        errorMes = MsgBox("No active CATIA document!" & vbNewLine & "Load a CATIA document and select at least one object.", vbCritical, "Error!")
            Err.Number = 0
    End If
    
End Sub

Attribute VB_Name = "leaderForm"
Attribute VB_Base = "0{3E47D10E-F40F-47BD-A4BC-E105E39A6285}{1EAA789E-EFB1-4AD3-907E-C4948A2DD4D5}"
Attribute VB_GlobalNameSpace = False
Attribute VB_Creatable = False
Attribute VB_PredeclaredId = True
Attribute VB_Exposed = False
Attribute VB_TemplateDerived = False
Attribute VB_Customizable = False


'Private Sub UserForm_Initialize()   'do this when form opens
'
'    Dim documents1 As Documents 'fill drop-down list with all open part documents
'    Set documents1 = CATIA.Documents
'
'    Dim partCount As Integer
'    partCount = documents1.Count
'
'    Dim partName As String
'
'        For i = 1 To partCount
'            partName = documents1.item(i).Name
'                targetPartCbox.AddItem partName
'        Next
'End Sub

Private Sub okButton_Click()
On Error Resume Next
        
    targetPart = targetPartCbox.Value
        letterL = textboxLetterL.Value
            numberL = textboxNumberL.Value
            
            If textboxLetterL.Value = "" Or IsNumeric(textboxLetterL.Value) = True Then
                MsgBox "Please input a index letter!", vbCritical, "Missing information!"
            ElseIf textboxNumberL.Value = "" Or IsNumeric(textboxNumberL.Value) = False Then
                MsgBox "Please input a starting number!", vbCritical, "Missing information!"
            ElseIf textboxNumberL.Value = 0 Then
                MsgBox "Index number can't be zero! Please try again.", vbCritical, "Can't be zero!"    'num can't be zero
            ElseIf Int(textboxNumberL.Value) / textboxNumberL.Value <> 1 Then          'is num a integer?
                MsgBox "Incorrect index number! Please try again.", vbCritical, "Not an integer!"
            Else
                Me.Hide
                    textboxLetterL.Text = ""
                    textboxNumberL.Text = ""
            End If
End Sub

Private Sub CancelButton_Click()    'closes the form
    Unload Me
End Sub

Private Sub UserForm_QueryClose(Cancel As Integer, CloseMode As Integer)    'together with cancel button terminates the whole macro
    End
End Sub

Attribute VB_Name = "mainForm"
Attribute VB_Base = "0{1A140487-0F40-49E5-A9B9-7C7F121D2BEE}{AE9617C2-BD08-439F-A7C2-4F3EACC94B39}"
Attribute VB_GlobalNameSpace = False
Attribute VB_Creatable = False
Attribute VB_PredeclaredId = True
Attribute VB_Exposed = False
Attribute VB_TemplateDerived = False
Attribute VB_Customizable = False
'Created by Per Björk, Engineering Partner

Private Sub MultiPage1_Change()

End Sub

Private Sub UserForm_Initialize()   'do this when form opens
    Dim objName As String
        Dim winName As String
            Dim winCount As Integer         'count windows and display the names in drop down box
                winCount = CATIA.Windows.Count
    
    For i = 1 To winCount
        winName = CATIA.Windows.Item(i).Name
            catTargetDrwCbox.AddItem winName
    Next
    
        catTolCbox.AddItem "±1", 0    'catia tolerances
        catTolCbox.AddItem "±2", 1
        catTolCbox.AddItem "±3", 2
        catTolCbox.AddItem "±4", 3
        catTolCbox.AddItem "±5", 4
        catTolCbox.AddItem "±6", 5
        
            XLtolCbox.AddItem "±1", 0
            XLtolCbox.AddItem "±2", 1
            XLtolCbox.AddItem "±3", 2
            XLtolCbox.AddItem "±4", 3
            XLtolCbox.AddItem "±5", 4
            XLtolCbox.AddItem "±6", 5
            
    'empty old values
    catTargetDrwCbox.Text = ""
    catHeadlineTbox.Text = ""
    catPointIndexTbox.Text = ""
    catTolCbox.Text = ""
        XLheadlineTbox.Text = ""
        XLpointIndexTbox.Text = ""
        XLtolCbox.Text = ""
            manXtbox.Text = ""
            manYtbox.Text = ""
            manZtbox.Text = ""
                lbSelection.Value = ""
    
    For s = 1 To selection1.Count
        objName = selection1.Item(s).Value.Name
            lbSelection.AddItem objName
    Next
End Sub

Private Sub UserForm_QueryClose(Cancel As Integer, CloseMode As Integer)    'together with cancel button terminates the whole macro
    End
End Sub

Private Sub catPolylineBut_Click()
    targetDrw = catTargetDrwCbox.Value
        headline = catHeadlineTbox.Value
            pointIndex = catPointIndexTbox.Value
                tol = catTolCbox.Value
        
    manX = manXtbox.Value
    manY = manYtbox.Value
    manZ = manZtbox.Value
        
        If catTargetDrwCbox.Value = "" Then    'user feedback controls
            MsgBox "Please select a target drawing!", vbCritical, "Missing information!"
        ElseIf catHeadlineTbox.Value = "" Then
            MsgBox "Please input a table headline!", vbCritical, "Missing information!"
        ElseIf catPointIndexTbox.Value = "" Then
            MsgBox "Please input a point index !", vbCritical, "Missing information!"
        Else
            Me.Hide
                userChoice = 1
        End If
End Sub

Private Sub catInvPolylineBut_Click()
    targetDrw = catTargetDrwCbox.Value
        headline = catHeadlineTbox.Value
            pointIndex = catPointIndexTbox.Value
                tol = catTolCbox.Value
    
    manX = manXtbox.Value
    manY = manYtbox.Value
    manZ = manZtbox.Value
    
        If catTargetDrwCbox.Value = "" Then    'user feedback controls
            MsgBox "Please select a target drawing!", vbCritical, "Missing information!"
        ElseIf catHeadlineTbox.Value = "" Then
            MsgBox "Please input a table headline!", vbCritical, "Missing information!"
        ElseIf catPointIndexTbox.Value = "" Then
            MsgBox "Please input a point index !", vbCritical, "Missing information!"
        Else
            Me.Hide
                userChoice = 2
        End If
End Sub

Private Sub catPointsBut_Click()
    targetDrw = catTargetDrwCbox.Value
        headline = catHeadlineTbox.Value
            pointIndex = catPointIndexTbox.Value
    
    manX = manXtbox.Value
    manY = manYtbox.Value
    manZ = manZtbox.Value
    
        If catTargetDrwCbox.Value = "" Then    'user feedback controls
            MsgBox "Please select a target drawing!", vbCritical, "Missing information!"
        ElseIf catHeadlineTbox.Value = "" Then
            MsgBox "Please input a table headline!", vbCritical, "Missing information!"
        ElseIf catPointIndexTbox.Value = "" Then
            MsgBox "Please input a point index!", vbCritical, "Missing information!"
        Else
            Me.Hide
                userChoice = 3
        End If
End Sub

Private Sub catCancelBut_Click()    'closes the form
    Unload Me
End Sub

Private Sub XLPolylineBut_Click()
    headline = XLheadlineTbox.Value
        pointIndex = XLpointIndexTbox.Value
            tol = XLtolCbox.Value
                    
    manX = manXtbox.Value
    manY = manYtbox.Value
    manZ = manZtbox.Value
                    
        If XLheadlineTbox.Value = "" Then
            MsgBox "Please input a table headline!", vbCritical, "Missing information!"
        ElseIf XLpointIndexTbox.Value = "" Then
            MsgBox "Please input a point index!", vbCritical, "Missing information!"
        Else
            Me.Hide
                userChoice = 4
        End If
End Sub

Private Sub XLinvPolylineBut_Click()
    headline = XLheadlineTbox.Value
        pointIndex = XLpointIndexTbox.Value
            tol = XLtolCbox.Value
            
    manX = manXtbox.Value
    manY = manYtbox.Value
    manZ = manZtbox.Value
            
        If XLheadlineTbox.Value = "" Then
            MsgBox "Please input a table headline!", vbCritical, "Missing information!"
        ElseIf XLpointIndexTbox.Value = "" Then
            MsgBox "Please input a point index!", vbCritical, "Missing information!"
        Else
            Me.Hide
                userChoice = 5
        End If
End Sub

Private Sub XLpointsBut_Click()
    headline = XLheadlineTbox.Value
        pointIndex = XLpointIndexTbox.Value
            
    manX = manXtbox.Value
    manY = manYtbox.Value
    manZ = manZtbox.Value
            
        If XLheadlineTbox.Value = "" Then
            MsgBox "Please input a table headline!", vbCritical, "Missing information!"
        ElseIf XLpointIndexTbox.Value = "" Then
            MsgBox "Please input a point index!", vbCritical, "Missing information!"
        Else
            Me.Hide
                userChoice = 6
        End If
End Sub

Private Sub XLcancelBut_Click()
    Unload Me
End Sub

Attribute VB_Name = "tableMacro"
'****************************************************************************
'This macro creates drawing tables in Catia and Excel for selected polyline and points.
'X, Y, Z coordinates, radius for each point and total length of the polyline.

'Instructions for use:
'Select item(s) and run macro, select target drawing, input table headline and letter.
'Table with coordinates will be created in the view "TABLES" on selected drawing.

'Created by Per Björk, Engineering Partner 2014
'****************************************************************************

'variables
Dim Coords(2) As Variant
Dim TheMeasurable As Variant
Dim errorMes As Variant
Dim polyline1NrOfElements As Integer
Dim numberOfPoints As Integer
Dim foundTables As Boolean
Dim errorRep As Boolean

Dim objGEXCELapp As Object
Dim objGEXCELwkBks As Object
Dim objGEXCELwkBk As Object
Dim objGEXCELwkShs As Object
Dim objGEXCELSh As Object

Public selection1 As Selection
Public targetDrw As String
Public headline As String
Public pointIndex As String
Public tol As String
Public userChoice As Integer

Public manX As Variant
Public manY As Variant
Public manZ As Variant

Sub CATMain()
On Error GoTo errorHandler  'errorhandlng
    
        'Dim selection1 As Selection
        Set selection1 = CATIA.ActiveDocument.Selection 'handle the selection in catia
            If selection1.Count = 0 Then    'if selection is empty display message
                MsgBox ("Nothing selected! Please select a polyline or at least one point.")
                    Exit Sub
            End If

                Load mainForm       'load main form
                    mainForm.Show
                    
                        If manX = "" Then
                            manX = 0
                        End If
                            
                            If manY = "" Then
                                manY = 0
                            End If
                        
                                If manZ = "" Then
                                    manZ = 0
                                End If
                    
                    If userChoice = 1 Or userChoice = 2 Then  'user choose to create a polyline table
                        catPolyline
                    ElseIf userChoice = 3 Then  'user choose to create a point table
                        catPoints
                    ElseIf userChoice = 4 Or userChoice = 5 Then
                        XLpolyline
                    ElseIf userChoice = 6 Then
                        XLpoints
                    End If

errorHandler:   'error messages
    If Err.Number = -2147467259 Then
        errorMes = MsgBox("No active 3D document!" & vbNewLine & "Load a 3D document and select a polyline or at least one point.", vbCritical, "Error!")
            Err.Number = 0
    End If
End Sub

Sub catPolyline()
On Error GoTo errorHandler  'errorhandlng
    
            'handle the selection in catia
            Set selection1 = CATIA.ActiveDocument.Selection
                Set polyline1 = selection1.Item(1)  'pick first element (the polyline) of the selection in Catia
                    If polyline1.Type <> "HybridShapePolyline" Then     'check if the object selected is a polyline
                        errorMes = MsgBox("Wrong type of object selected! Please select a polyline.", vbCritical, "Wrong type of object!!")
                        Exit Sub
                    End If
                    
                    Set myPolyline = polyline1.Value
                        polyline1NrOfElements = myPolyline.NumberOfElements  'count number of points in the polyline
'********************************************************************************************************************************
    'start table creation process
    CATIA.Windows.Item(targetDrw).Activate     'switch to drawing window
        Set myDoc = CATIA.ActiveDocument    'define active document and view
            Set mySheet = myDoc.Sheets.ActiveSheet
    
                For i = 1 To mySheet.Views.Count                'check if drawing view "TABLES" exists
                    Set myView = mySheet.Views.Item(i)      'set view
                        If myView.Name = "TABLES" Then             'if "TABLES" exists activate view and exit for-loop
                            Set myView = mySheet.Views.Item("TABLES")
                                myView.Activate
                                    foundTables = True
                                        Exit For
                        End If
                Next
        
                        If foundTables = False Then             'if "TABLES" doesn't exist, create it and activate
                            Set myView = mySheet.Views.Add("TABLES")
                                myView.Activate
                        End If

        'create the table itself
        Dim mytable As DrawingTable
        Set mytable = myView.Tables.Add(100, 100, polyline1NrOfElements + 3, 5, 7.5, 22)
    
            'add labels
            mytable.SetCellString 1, 1, headline
            mytable.SetCellString 2, 1, "POINT"
            mytable.SetCellString 2, 2, "X"
            mytable.SetCellString 2, 3, "Y"
            mytable.SetCellString 2, 4, "Z"
            mytable.SetCellString 2, 5, "RADIUS"
                'format the table
                mytable.MergeCells 1, 1, 1, 5
                    mytable.SetCellAlignment 1, 1, CatTableTopCenter
                mytable.MergeCells polyline1NrOfElements + 3, 1, 1, 5
                    mytable.SetCellAlignment polyline1NrOfElements + 3, 1, CatTableTopCenter
'**************************************************************************************************************************************
    'coordinate extraction process
    Dim TheSPAWorkbench As Workbench
    Set TheSPAWorkbench = CATIA.ActiveDocument.GetWorkbench("SPAWorkbench") ' set TheSPAWorkbench
        Dim pointRef As Reference
            Dim oRad As Length
'**************************************************************************************************************************************
            If userChoice = 1 Then  'normal polyline
                For i = 1 To polyline1NrOfElements       'iterate through all poinst of polyline
                    myPolyline.GetElement i, pointRef, oRad
                            
                    'set refObject
                    Set TheMeasurable = TheSPAWorkbench.GetMeasurable(pointRef)             ' set Measurable with reference
                        TheMeasurable.GetPoint Coords                                           ' get coordinates from Measurable
                    Set MeasureLength = TheSPAWorkbench.GetMeasurable(myPolyline)
                        myPolylineLength = MeasureLength.Length
                        
                    If oRad Is Nothing Then RadiusAtPoint = False Else: RadiusAtPoint = True                ' check if Radius at point
                                       
                    'add point index
                    mytable.SetCellString 2 + i, 1, pointIndex & i
                    
                    xPoint = Coords(0)
                    Coords(0) = xPoint + manX
                    xPoint = Round(Coords(0), 1) 'check decimals
                        If xPoint = 0 Then      'avoid division with zero
                            mytable.SetCellString 2 + i, 2, "0,0"       'add "0,0"
                        ElseIf Int(xPoint) / xPoint = 1 Then        'check if integer
                            mytable.SetCellString 2 + i, 2, xPoint & ",0"       'add ",0"
                        Else
                            mytable.SetCellString 2 + i, 2, Round(Coords(0), 1)    'else, use 1 decimal
                        End If
                    
                    yPoint = Coords(1)
                    Coords(1) = yPoint + manY
                    yPoint = Round(Coords(1), 1)       'same procedure for y and z
                        If yPoint = 0 Then
                            mytable.SetCellString 2 + i, 3, "0,0"
                        ElseIf Int(yPoint) / yPoint = 1 Then
                            mytable.SetCellString 2 + i, 3, yPoint & ",0"
                        Else
                            mytable.SetCellString 2 + i, 3, Round(Coords(1), 1)
                        End If
        
                    zPoint = Coords(2)
                    Coords(2) = zPoint + manZ
                    zPoint = Round(Coords(2), 1)
                        If zPoint = 0 Then
                            mytable.SetCellString 2 + i, 4, "0,0"
                        ElseIf Int(zPoint) / zPoint = 1 Then
                            mytable.SetCellString 2 + i, 4, zPoint & ",0"
                        Else
                            mytable.SetCellString 2 + i, 4, Round(Coords(2), 1)
                        End If
                                        
                    If RadiusAtPoint Then
                        radPoint = Round(oRad.Value, 1)     'same method as above
                            If radPoint = 0 Then
                                mytable.SetCellString 2 + i, 5, ""
                            ElseIf Int(radPoint) / radPoint = 1 Then
                                mytable.SetCellString 2 + i, 5, radPoint & ",0"
                            Else
                                mytable.SetCellString 2 + i, 5, Round(oRad.Value, 1)
                            End If
                    End If
                Next
 '**************************************************************************************************************************************************
            ElseIf userChoice = 2 Then  'inverted polyline
                x = 1
                For i = polyline1NrOfElements To 1 Step -1        'iterate through all poinst of polyline
                    myPolyline.GetElement i, pointRef, oRad
                            
                    'set refObject
                    Set TheMeasurable = TheSPAWorkbench.GetMeasurable(pointRef)             ' set Measurable with reference
                        TheMeasurable.GetPoint Coords                                           ' get coordinates from Measurable
                    Set MeasureLength = TheSPAWorkbench.GetMeasurable(myPolyline)
                        myPolylineLength = MeasureLength.Length
                        
                    If oRad Is Nothing Then RadiusAtPoint = False Else: RadiusAtPoint = True                ' check if Radius at point
                    
                    mytable.SetCellString 2 + x, 1, pointIndex & x  'set point ref
            
                        xPoint = Coords(0)
                        Coords(0) = xPoint + manX
                        xPoint = Round(Coords(0), 1) 'check decimals
                            If xPoint = 0 Then      'avoid division with zero
                                mytable.SetCellString (2 + i) - (i - x), 2, "0,0" 'add "0,0"
                            ElseIf Int(xPoint) / xPoint = 1 Then        'check if integer
                                mytable.SetCellString (2 + i) - (i - x), 2, xPoint & ",0"      'add ",0"
                            Else
                                mytable.SetCellString (2 + i) - (i - x), 2, Round(Coords(0), 1)     'else, use 1 decimal
                            End If
                        
                        yPoint = Coords(1)
                        Coords(1) = yPoint + manY
                        yPoint = Round(Coords(1), 1)        'same procedure for y and z
                            If yPoint = 0 Then
                                mytable.SetCellString (2 + i) - (i - x), 3, "0,0"
                            ElseIf Int(yPoint) / yPoint = 1 Then
                                mytable.SetCellString (2 + i) - (i - x), 3, yPoint & ",0"
                            Else
                                mytable.SetCellString (2 + i) - (i - x), 3, Round(Coords(1), 1)
                            End If
            
                        zPoint = Coords(2)
                        Coords(2) = zPoint + manZ
                        zPoint = Round(Coords(2), 1)
                            If zPoint = 0 Then
                                mytable.SetCellString (2 + i) - (i - x), 4, "0,0"
                            ElseIf Int(zPoint) / zPoint = 1 Then
                                mytable.SetCellString (2 + i) - (i - x), 4, zPoint & ",0"
                            Else
                                mytable.SetCellString (2 + i) - (i - x), 4, Round(Coords(2), 1)
                            End If
                                            
                        If RadiusAtPoint Then
                            radPoint = Round(oRad.Value, 1)     'same method as above
                                If radPoint = 0 Then
                                    mytable.SetCellString (2 + i) - (i - x), 5, ""
                                ElseIf Int(radPoint) / radPoint = 1 Then
                                    mytable.SetCellString (2 + i) - (i - x), 5, radPoint & ",0"
                                Else
                                    mytable.SetCellString (2 + i) - (i - x), 5, Round(oRad.Value, 1)
                                End If
                        End If
                        
                    x = x + 1   'add 1 to x for every turn of the loop
                Next
            End If
'****************************************************************************************************************************************
                polyLength = Round(myPolylineLength, 1)  'add length, check integer, same method as above
                    If Int(polyLength) / polyLength = 1 Then
                        mytable.SetCellString polyline1NrOfElements + 3, 1, "TOTAL LENGTH = " & polyLength & ",0" & tol & " MM"
                    Else
                        mytable.SetCellString polyline1NrOfElements + 3, 1, "TOTAL LENGTH = " & Round(myPolylineLength, 1) & tol & " MM"
                    End If
                    
                MsgBox "Polyline coordinate table created!"  'display message of completion
'***************************************************************************************************************************************************
errorHandler:   'error messages
    If Err.Number = 438 Then
        errorMes = MsgBox("Can't create drawing table in a 3D document! Please select window containing the target drawing.", vbCritical, "Error!")
            Err.Number = 0
                Exit Sub
    ElseIf Err.Number = -2147467259 Then
        errorMes = MsgBox("Wrong type of object(s) selected! This function only works with point items.", vbCritical, "Error!")
            Err.Number = 0
    End If
End Sub

Sub catPoints()
On Error GoTo errorHandler  'set up errorhandler

    Dim selection1 As Selection 'handle selection
    Set selection1 = CATIA.ActiveDocument.Selection
        numberOfPoints = selection1.Count
    
    'start table creation process
    CATIA.Windows.Item(targetDrw).Activate     'switch to drawing window
        Set myDoc = CATIA.ActiveDocument    'define active document and view
            Set mySheet = myDoc.Sheets.ActiveSheet
            
    For i = 1 To mySheet.Views.Count                'check if drawing view "TABLES" exists
        Set myView = mySheet.Views.Item(i)      'set view
            If myView.Name = "TABLES" Then             'if "TABLES" exists activate view and exit for loop
                Set myView = mySheet.Views.Item("TABLES")
                    myView.Activate
                        foundTables = True
                            Exit For
            End If
    Next
        
            If foundTables = False Then             'if "TABLES" doesn't exist, create and activate it
                Set myView = mySheet.Views.Add("TABLES")
                    myView.Activate
            End If
        
        'create the table itself
        Dim mytable As DrawingTable
        Set mytable = myView.Tables.Add(100, 100, numberOfPoints + 2, 4, 7.5, 23)
        'add labels
        mytable.SetCellString 1, 1, headline
        mytable.SetCellString 2, 1, "POINT"
        mytable.SetCellString 2, 2, "X"
        mytable.SetCellString 2, 3, "Y"
        mytable.SetCellString 2, 4, "Z"
        mytable.MergeCells 1, 1, 1, 4
        mytable.SetCellAlignment 1, 1, CatTableTopCenter
        
'**********************************************************************************************************************************************
    'coordinate extraction process
    Dim TheSPAWorkbench As Workbench
    Set TheSPAWorkbench = CATIA.ActiveDocument.GetWorkbench("SPAWorkbench") ' set TheSPAWorkbench
        Dim pointRef As Reference
            Dim oRad As Length
'**********************************************************************************************************************************************
    For i = 1 To numberOfPoints                 'create correct number of rows
        Set Element = selection1.Item(i)
            Set selPoint = Element.Value
        
        Set TheMeasurable = TheSPAWorkbench.GetMeasurable(selPoint)
            TheMeasurable.GetPoint Coords       'get coordinates from Measurable
                
            mytable.SetCellString 2 + i, 1, pointIndex & i  'add point index

                xPoint = Coords(0)
                Coords(0) = xPoint + manX
                xPoint = Round(Coords(0), 1) 'check decimals
                    If xPoint = 0 Then  'avoid division with zero
                        mytable.SetCellString 2 + i, 2, "0,0"   'add 0,0
                    ElseIf Int(xPoint) / xPoint = 1 Then        'if integer
                        mytable.SetCellString 2 + i, 2, xPoint & ",0"       'add ",0"
                    Else
                        mytable.SetCellString 2 + i, 2, Round(Coords(0), 1)     'else, use 1 decimal
                    End If
                
                yPoint = Coords(1)
                Coords(1) = yPoint + manY
                yPoint = Round(Coords(1), 1)        'same procedure for y and z
                    If yPoint = 0 Then
                        mytable.SetCellString 2 + i, 3, "0,0"
                    ElseIf Int(yPoint) / yPoint = 1 Then
                        mytable.SetCellString 2 + i, 3, yPoint & ",0"
                    Else
                        mytable.SetCellString 2 + i, 3, Round(Coords(1), 1)
                    End If

                zPoint = Coords(2)
                Coords(2) = zPoint + manZ
                zPoint = Round(Coords(2), 1)
                    If zPoint = 0 Then
                        mytable.SetCellString 2 + i, 4, "0,0"
                    ElseIf Int(zPoint) / zPoint = 1 Then
                        mytable.SetCellString 2 + i, 4, zPoint & ",0"
                    Else
                        mytable.SetCellString 2 + i, 4, Round(Coords(2), 1)
                    End If
        Next
        
        MsgBox "Point coordinate table created!" & vbNewLine & "Points are presented in order of selection."  'display message of completion
'***************************************************************************************************************************************************
errorHandler:   'error messages
    If Err.Number = 438 Then
        errorMes = MsgBox("Can't create drawing table in a 3D document! Please select window containing the target drawing.", vbCritical, "Error")
            Err.Number = 0
    ElseIf Err.Number = -2147467259 Then
        errorMes = MsgBox("Wrong type of object(s) selected! This function only works with point items.", vbCritical, "Error!")
            Err.Number = 0
    End If
End Sub

Sub XLpolyline()
On Error GoTo errorHandler
    
        'handle the selection in catia
        Set selection1 = CATIA.ActiveDocument.Selection
            Set polyline1 = selection1.Item(1)  'pick first element (the polyline) of the selection in Catia
                If polyline1.Type <> "HybridShapePolyline" Then     'check if the object selected is a polyline
                        errorMes = MsgBox("Wrong type of object selected! Please select a polyline.", vbCritical, "Wrong type of object!!")
                    Exit Sub
                End If
            Set myPolyline = polyline1.Value
                polyline1NrOfElements = myPolyline.NumberOfElements  'count number of points in the polyline
'************************************************************************************************************************************************
        StartEXCEL  'run Excel
        
        Dim TheSPAWorkbench As Workbench
        Set TheSPAWorkbench = CATIA.ActiveDocument.GetWorkbench("SPAWorkbench") 'set TheSPAWorkbench
            Dim pointRef As Reference
                Dim oRad  As Length
'************************************************************************************************************************************************
    If userChoice = 4 Then    'normal polyline
        For i = 1 To polyline1NrOfElements  'iterate through all poinst of polyline
            myPolyline.GetElement i, pointRef, oRad
                
                Set TheMeasurable = TheSPAWorkbench.GetMeasurable(pointRef)
                    TheMeasurable.GetPoint Coords                                           'get coordinates from Measurable
                Set MeasureLength = TheSPAWorkbench.GetMeasurable(myPolyline)
                    myPolylineLength = MeasureLength.Length

            If oRad Is Nothing Then RadiusAtPoint = False Else RadiusAtPoint = True ' check if Radius at point
             
            'write data to Excel sheet
            objGEXCELSh.cells(i + 2, "A") = pointIndex & i      'add point name

            xPoint = Coords(0)
            Coords(0) = xPoint + manX
            xPoint = Round(Coords(0), 1) 'check decimals
                If xPoint = 0 Then      'prevent divison by zero
                    objGEXCELSh.cells(i + 2, "B") = "0,0"       'add "0,0"
                ElseIf Int(xPoint) / xPoint = 1 Then        'check if integer
                    objGEXCELSh.cells(i + 2, "B") = xPoint & ",0"       'add ",0"
                Else
                    objGEXCELSh.cells(i + 2, "B") = Round(Coords(0), 1) 'else, use 1 decimal
                End If
                
            yPoint = Coords(1)
            Coords(1) = yPoint + manY
            yPoint = Round(Coords(1), 1)        'same procedure for y and z
                If yPoint = 0 Then
                    objGEXCELSh.cells(i + 2, "C") = "0,0"
                ElseIf Int(yPoint) / yPoint = 1 Then
                    objGEXCELSh.cells(i + 2, "C") = yPoint & ",0"
                Else
                    objGEXCELSh.cells(i + 2, "C") = Round(Coords(1), 1)
                End If
    
            zPoint = Coords(2)
            Coords(2) = zPoint + manZ
            zPoint = Round(Coords(2), 1)
                If zPoint = 0 Then
                    objGEXCELSh.cells(i + 2, "D") = "0,0"
                ElseIf Int(zPoint) / zPoint = 1 Then
                    objGEXCELSh.cells(i + 2, "D") = zPoint & ",0"
                Else
                    objGEXCELSh.cells(i + 2, "D") = Round(Coords(2), 1)
                End If
                
                    If RadiusAtPoint Then   'add radius value
                        radPoint = Round(oRad.Value, 1)     'same method as above
                            If radPoint = 0 Then
                                objGEXCELSh.cells(i + 2, "E") = ""
                            ElseIf Int(radPoint) / radPoint = 1 Then
                                objGEXCELSh.cells(i + 2, "E") = radPoint & ",0"
                            Else
                                objGEXCELSh.cells(i + 2, "E") = Round(oRad.Value, 1)
                            End If
                    End If
        Next
        
    ElseIf userChoice = 5 Then    'inverted polyline
        x = 1
        For i = polyline1NrOfElements To 1 Step -1  'iterate through all poinst of polyline
            
                myPolyline.GetElement i, pointRef, oRad
                    
                    Set TheMeasurable = TheSPAWorkbench.GetMeasurable(pointRef)
                        TheMeasurable.GetPoint Coords                       'get coordinates from Measurable
                    Set MeasureLength = TheSPAWorkbench.GetMeasurable(myPolyline)
                        myPolylineLength = MeasureLength.Length
    
                If oRad Is Nothing Then RadiusAtPoint = False Else RadiusAtPoint = True ' check if Radius at point
                 
                'write data to Excel sheet
                objGEXCELSh.cells(x + 2, "A") = pointIndex & x      'add point name
    
            xPoint = Coords(0)
            Coords(0) = xPoint + manX
            xPoint = Round(Coords(0), 1) 'check decimals
                If xPoint = 0 Then      'prevent divison by zero
                    objGEXCELSh.cells((2 + i) - (i - x), "B") = "0,0"       'add "0,0"  (2 + i) - (i - X), 2, "0,0" 'add "0,0"
                ElseIf Int(xPoint) / xPoint = 1 Then        'check if integer
                    objGEXCELSh.cells((2 + i) - (i - x), "B") = xPoint & ",0"       'add ",0"
                Else
                    objGEXCELSh.cells((2 + i) - (i - x), "B") = Round(Coords(0), 1) 'else, use 1 decimal
                End If
                
            yPoint = Coords(1)
            Coords(1) = yPoint + manY
            yPoint = Round(Coords(1), 1)        'same procedure for y and z
                If yPoint = 0 Then
                    objGEXCELSh.cells((2 + i) - (i - x), "C") = "0,0"
                ElseIf Int(yPoint) / yPoint = 1 Then
                    objGEXCELSh.cells((2 + i) - (i - x), "C") = yPoint & ",0"
                Else
                    objGEXCELSh.cells((2 + i) - (i - x), "C") = Round(Coords(1), 1)
                End If
    
            zPoint = Coords(2)
            Coords(2) = zPoint + manZ
            zPoint = Round(Coords(2), 1)
                If zPoint = 0 Then
                    objGEXCELSh.cells((2 + i) - (i - x), "D") = "0,0"
                ElseIf Int(zPoint) / zPoint = 1 Then
                    objGEXCELSh.cells((2 + i) - (i - x), "D") = zPoint & ",0"
                Else
                    objGEXCELSh.cells((2 + i) - (i - x), "D") = Round(Coords(2), 1)
                End If
                
                    If RadiusAtPoint Then   'add radius value
                        radPoint = Round(oRad.Value, 1)     'same method as above
                            If radPoint = 0 Then
                                objGEXCELSh.cells((2 + i) - (i - x), "E") = ""
                            ElseIf Int(radPoint) / radPoint = 1 Then
                                objGEXCELSh.cells((2 + i) - (i - x), "E") = radPoint & ",0"
                            Else
                                objGEXCELSh.cells((2 + i) - (i - x), "E") = Round(oRad.Value, 1)
                            End If
                    End If
         
        x = x + 1   'add 1 to x for every turn of the loop
        Next
    End If
'**********************************************************************************************************************************************************
                polyLength = Round(myPolylineLength, 1)  'add length, check integer, same method as aboove
                        If Int(polyLength) / polyLength = 1 Then
                            objGEXCELSh.cells(polyline1NrOfElements + 3, "A") = "TOTAL LENGTH = " & polyLength & ",0" & tol & " MM"
                        Else
                            objGEXCELSh.cells(polyline1NrOfElements + 3, "A") = "TOTAL LENGTH = " & Round(myPolylineLength, 1) & tol & " MM"    'the length
                        End If
                
                MsgBox "Coordinate extraction complete!"       'completion message
'**********************************************************************************************************************************************************
errorHandler:   'error messages
    If Err.Number = -2147467259 Then
        errorMes = MsgBox("Wrong type of object(s) selected! This function only works with point items.", vbCritical, "Error!")
            Err.Number = 0
    End If
End Sub

Sub XLpoints()
    On Error GoTo errorHandler  'errorhandler
    
    'set up selection
    Set selection1 = CATIA.ActiveDocument.Selection
        numberOfPoints = selection1.Count
'*******************************************************************************************************************
    StartEXCEL
'*******************************************************************************************************************
    Dim TheSPAWorkbench As Workbench
    Set TheSPAWorkbench = CATIA.ActiveDocument.GetWorkbench("SPAWorkbench")     'set TheSPAWorkbench
        Dim pointRef As Reference
            Dim oRad As Length
'*******************************************************************************************************************
    For i = 1 To selection1.Count       'go through the selected points
        Set Element = selection1.Item(i)
            Set selPoint = Element.Value
        
            Set TheMeasurable = TheSPAWorkbench.GetMeasurable(selPoint)
                TheMeasurable.GetPoint Coords              'get coordinates from Measurable

        objGEXCELSh.cells(i + 2, "A") = pointIndex & i  'add point prefix
        
        xPoint = Coords(1)
        Coords(1) = xPoint + manX
        xPoint = Round(Coords(1), 1)        'same procedure for y and z
            If xPoint = 0 Then      'prevent division by zero
                objGEXCELSh.cells(i + 2, "B") = "0,0"       'add "0,0"
            ElseIf Int(xPoint) / xPoint = 1 Then        'check if integer
                objGEXCELSh.cells(i + 2, "B") = xPoint & ",0"       'add ",0"
            Else
                objGEXCELSh.cells(i + 2, "B") = Round(Coords(0), 1) 'else, use 1 decimal
            End If
            
        yPoint = Coords(2)
        Coords(2) = yPoint + manY
        yPoint = Round(Coords(2), 1)
            If yPoint = 0 Then
                objGEXCELSh.cells(i + 2, "C") = "0,0"
            ElseIf Int(yPoint) / yPoint = 1 Then
                objGEXCELSh.cells(i + 2, "C") = yPoint & ",0"
            Else
                objGEXCELSh.cells(i + 2, "C") = Round(Coords(1), 1)
            End If

        zPoint = Coords(2)
        Coords(2) = zPoint + manZ
        zPoint = Round(Coords(2), 1)
            If zPoint = 0 Then
                objGEXCELSh.cells(i + 2, "D") = "0,0"
            ElseIf Int(zPoint) / zPoint = 1 Then
                objGEXCELSh.cells(i + 2, "D") = zPoint & ",0"
            Else
                objGEXCELSh.cells(i + 2, "D") = Round(Coords(2), 1)
            End If
    Next
            MsgBox "Coordinate extraction complete!" & vbNewLine & "Points are presented in order of selection."    'display completion message
'**************************************************************************************************************************************************
errorHandler:   'error message
    If Err.Number = -2147467259 Then
        errorMes = MsgBox("Wrong type of object(s) selected! This function only works with point items.", vbCritical, "Error!")
            Err.Number = 0
    End If
    
End Sub

Sub StartEXCEL()    'function for opening excel
    Err.Clear
        On Error Resume Next    'error handling
            Set objGEXCELapp = GetObject(, "EXCEL.Application")     'start Excel

    If Err.Number <> 0 Then
        Err.Clear
            Set objGEXCELapp = CreateObject("EXCEL.Application")
    End If
'*****************************************************************************************************************
    objGEXCELapp.Application.Visible = True
        Set objGEXCELwkBks = objGEXCELapp.Application.WorkBooks     'prepare excel worksheets
        Set objGEXCELwkBk = objGEXCELwkBks.Add
        Set objGEXCELwkShs = objGEXCELwkBk.Worksheets(1)
        Set objGEXCELSh = objGEXCELwkBk.Sheets(1)
            objGEXCELSh.cells(1, "A") = headline         'add table headlines
            objGEXCELSh.cells(2, "A") = "POINT"
            objGEXCELSh.cells(2, "B") = "X"
            objGEXCELSh.cells(2, "C") = "Y"
            objGEXCELSh.cells(2, "D") = "Z"
            If userChoice <> 6 Then
                objGEXCELSh.cells(2, "E") = "RADIUS"    'add only "RADIUS" for polylines
            End If
End Sub
