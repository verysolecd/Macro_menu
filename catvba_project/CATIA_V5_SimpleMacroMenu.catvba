Attribute VB_Name = "Button_Evt"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'VERSION 1.0 CLASS
'Begin
'  MultiUse = -1  'True
'End
'Attribute VB_Name = "Button_Evt"
'Attribute VB_GlobalNameSpace = False
'Attribute VB_Creatable = False
'Attribute VB_PredeclaredId = False
'Attribute VB_Exposed = False
'' Button_Evt.cls
'' 此代码用于处理按钮事件

'Attribute mBtn.VB_VarHelpID = -1
' Cat_Macro_Menu_Model.bas
' 定义全局变量（防止命名冲突）

Option Explicit

Private WithEvents mBtn As MSForms.CommandButton
Attribute mBtn.VB_VarHelpID = -1
Private mInfo As Object
Private mParentForm As MSForms.UserForm
Private mCloseType As Boolean
Private Const TAG_ENTRYPNT = "ep"           ' 入口点标签
Private Const TAG_PJTPATH = "pjt_path"      ' 项目路径标签
Private Const TAG_MDLNAME = "mdl_name"      ' 模块名称标签

' 设置事件
Sub set_ButtonEvent(ByVal btn As MSForms.CommandButton, _
              ByVal BtnInfo As Object, _
              ByVal ParentForm As MSForms.UserForm, _
              ByVal CloseType As Boolean)
    Set mBtn = btn
    Set mInfo = BtnInfo
    Set mParentForm = ParentForm
    mCloseType = CloseType
End Sub
' 按钮点击事件处理
'Private Sub mBtn_Click()
'    If Not mCloseType Then Unload mParentForm
'    Dim ary: ary = Array()
'    Dim ss: Set ss = CATIA.SystemService
'    Call ss.ExecuteScript(mInfo(TAG_PJTPATH), _
'                          catScriptLibraryTypeVBAProject, _
'                          mInfo(TAG_MDLNAME), _
'                          mInfo(TAG_ENTRYPNT), _
'                          Array())
'End Sub


Private Sub mBtn_Click()
    If Not mCloseType Then Unload mParentForm
    ' 如果是颜色切换按钮，在执行前更新按钮文字
    If mInfo(TAG_MDLNAME) = "M60_Color" Then
        On Error Resume Next
        Dim MyViewer
        Set MyViewer = CATIA.activeWindow.ActiveViewer
         Dim currentColor(2)
        MyViewer.GetBackgroundColor currentColor
        On Error GoTo 0
        ' 根据当前背景色判断即将切换到的状态
        Dim willBeWhite As Boolean
        willBeWhite = (currentColor(0) <> 1 Or currentColor(1) <> 1 Or currentColor(2) <> 1)
        
        ' 调用M60_Color模块的函数更新按钮文字
        Call M60_Color.UpdateButtonText(mBtn, willBeWhite)
    End If
    
    Dim ary: ary = Array()
    Dim ss: Set ss = CATIA.SystemService
    
    Call ss.ExecuteScript(mInfo(TAG_PJTPATH), _
                          catScriptLibraryTypeVBAProject, _
                          mInfo(TAG_MDLNAME), _
                          mInfo(TAG_ENTRYPNT), _
                          Array())
End Sub

Attribute VB_Name = "Cat_Macro_Menu_View"
Attribute VB_Base = "0{86BFA51B-B1C9-4A30-8A72-88B4F1D895CA}{67C57F34-0D11-40FA-B035-6585A0D9C09F}"
Attribute VB_GlobalNameSpace = False
Attribute VB_Creatable = False
Attribute VB_PredeclaredId = True
Attribute VB_Exposed = False
Attribute VB_TemplateDerived = False
Attribute VB_Customizable = False
' VERSION 5.00
' Begin {C62A69F0-16DC-11CE-9E98-00AA00574A4F} Cat_Macro_Menu_View
   ' Caption         =   "UserForm1"
   ' ClientHeight    =   7995
   ' ClientLeft      =   120
   ' ClientTop       =   450
   ' ClientWidth     =   11595
   ' OleObjectBlob   =   "Cat_Macro_Menu_View.frx":0000
   ' StartUpPosition =   1  'CenterOwner
' End
' Attribute VB_Name = "Cat_Macro_Menu_View"
' Attribute VB_GlobalNameSpace = False
' Attribute VB_Creatable = False
' Attribute VB_PredeclaredId = True
' Attribute VB_Exposed = False
'Attribute lblAuthor.VB_VarHelpID = -1
'Attribute MPgs.VB_VarHelpID = -1
'Attribute prdObserver.VB_VarHelpID = -1
'Attribute lblProductInfo.VB_VarHelpID = -1
' 窗体边距
Private FrmMargin As Variant ' 上, 右, 下, 左 窗体边距调整值
' 窗体宽度调整值
Private Const ADJUST_F_W = 4
' 窗体高度调整值
Private Const ADJUST_F_H = 4
' 多页控件调整
Private Const ADJUST_M_W = 15 ' 多页控件宽度调整值
Private Const ADJUST_M_H = 40 ' 多页控件高度调整值
Private Const Tab_W = 30 ' Tab固定宽度
Private Const Tab_H = 19 ' TAB高度
Private Const Tab_frontsize = 10
' 按钮尺寸
Private Const BTN_W = 70 ' 按钮的固定宽度
Private Const BTN_H = 20 ' 单个按钮的高度
Private Const BTN_frontsize = 8 ' 按钮字体大小
'标签尺寸
Private Const lb_W = 62 ' 宽度
Private Const lb_H = 18 ' 高度
Private Const lb_frontsize = 10 ' 字体大小
Private mBtns As Object ' 按钮事件集合
Private WithEvents prdObserver As ProductObserver
Attribute prdObserver.VB_VarHelpID = -1
Private WithEvents lblProductInfo As MSForms.Label
Attribute lblProductInfo.VB_VarHelpID = -1
Private WithEvents lblAuthor As MSForms.Label
Attribute lblAuthor.VB_VarHelpID = -1
Private WithEvents MPgs As MSForms.MultiPage
Attribute MPgs.VB_VarHelpID = -1
Private Const itl = "公众号:键盘造车手"
Option Explicit
' 设置窗体信息
Sub Set_FormInfo(ByVal InfoLst As Object, _
                 ByVal PageMap As Object, _
                 ByVal FormTitle As String, _
                 ByVal CloseType As Boolean)
         ' 连接到全局产品观察者
    Set prdObserver = ProductObserver
    ' 初始化窗体边距
    FrmMargin = Array(2, 2, 2, 2) ' 上, 右, 下, 左 窗体边距调整值
    ' 创建多页控件
    Set MPgs = Me.Controls.Add("Forms.MultiPage.1", "MPgs", True)
    Dim Pgs As Pages
     Set Pgs = MPgs.Pages
     Pgs.Clear
    Dim Key As Long, KeyStr As Variant
    Dim Pg As Page, pName As String
    Dim BtnInfos As Object, Info As Variant
    Dim Btns As Object: Set Btns = KCL.InitLst()
    Dim btn As MSForms.CommandButton
    Dim BtnEvt As Button_Evt
    For Each KeyStr In InfoLst
        Key = CLng(KeyStr)
        If Not PageMap.Exists(Key) Then GoTo continue
        pName = PageMap(Key)
        Set Pg = Get_Page(Pgs, pName)
        Set BtnInfos = InfoLst(KeyStr)
        For Each Info In BtnInfos
            Set btn = Init_Button(Pg.Controls, Key, Info)
            Set BtnEvt = New Button_Evt
            Call BtnEvt.set_ButtonEvent(btn, Info, Me, CloseType)
            Btns.Add BtnEvt
        Next
continue:
    Next
        Set mBtns = Btns
    Call Set_MPage(MPgs)
    Call Set_Form(MPgs, FormTitle)
    Set lblProductInfo = Me.Controls.Add("Forms.Label.1", "lblProductInfo", True)
   With lblProductInfo
        .Caption = "产品待选择"
        .Top = FrmMargin(0)
        .Left = 2
        .Width = MPgs.Width - 20
        .Height = lb_H
        .Font.Size = lb_frontsize
        .BackColor = vbGreen
        .TextAlign = fmTextAlignCenter
        .BorderStyle = fmBorderStyleSingle
        .WordWrap = False              ' 不换行
         .AutoSize = True
    End With
    ' 新增：创建底部的作者信息栏
    Set lblAuthor = Me.Controls.Add("Forms.Label.1", "lblAuthor", True)
    With lblAuthor
        .Caption = itl ' 使用常量显示作者信息
        .Top = MPgs.Top + MPgs.Height + FrmMargin(1) ' 放置在多页控件下方
        .Left = lblProductInfo.Left + 5 ' 与顶部信息栏左对齐
        .Width = lblProductInfo.Width ' 与顶部信息栏同宽
        .Height = lb_H
        .Font.Size = lb_frontsize - 1 ' 字体可以稍小一些
        .TextAlign = fmTextAlignCenter
         .WordWrap = False              ' 不换行
         .AutoSize = True
          .BorderStyle = fmBorderStyleSingle
    End With
    ' 初始更新产品信息
    UpdateProductInfo
End Sub
' 设置窗体属性
Private Sub Set_Form(ByVal MPgs As MultiPage, ByVal Cap As String)
    With Me
        Dim requiredInsideHeight
        requiredInsideHeight = MPgs.Top + MPgs.Height + lb_H + FrmMargin(2) + ADJUST_F_H
        .Height = requiredInsideHeight + (Me.Height - Me.InsideHeight)
        .Width = MPgs.Width + ADJUST_F_W
        .Caption = Cap
    End With
End Sub
' 设置多页控件属性
Private Sub Set_MPage(ByVal MPgs As MultiPage)
    MPgs.Width = FrmMargin(1) + Tab_W + BTN_W + FrmMargin(3) + ADJUST_M_W
    With MPgs
        .Top = lb_H + FrmMargin(1)
        .Left = FrmMargin(0)
        .TabFixedHeight = Tab_H  ' 标签高度（单位：磅）
        .TabFixedWidth = Tab_W ' 标签宽度
        .Font.Name = "Arial"
        .Font.Size = Tab_frontsize
        .MultiRow = True
        .TabOrientation = fmTabOrientationLeft
        .Style = fmTabStyleButtons  ' 切换为按钮样式
     End With
    Dim Pg As Page
    Dim MaxBtnCnt As Long: MaxBtnCnt = 0
    Dim BtnCnt As Long
    For Each Pg In MPgs.Pages
        BtnCnt = Pg.Controls.Count
        MaxBtnCnt = IIf(BtnCnt > MaxBtnCnt, BtnCnt, MaxBtnCnt)
    Next
    MPgs.Height = FrmMargin(0) + (BTN_H * MaxBtnCnt * 1.1) + FrmMargin(2) + ADJUST_M_H
    ' 设置多页控件背景颜色
End Sub
' 初始化按钮
Private Function Init_Button(ByVal Ctls As Controls, _
                             ByVal idx As Long, _
                             ByVal BtnInfo As Variant) As MSForms.CommandButton
    Dim btn As MSForms.CommandButton
    Set btn = Ctls.Add("Forms.CommandButton.1", idx, True)
    Dim Pty As Variant
    For Each Pty In BtnInfo.keys
        Call Try_SetProperty(btn, Pty, BtnInfo.item(Pty))
    Next
    With btn
        .Top = FrmMargin(0) + (Ctls.Count - 1) * BTN_H
        .Left = FrmMargin(2)
        .Height = BTN_H
        .Width = BTN_W
        ' 设置按钮字体
        .Font.Name = "Arial"
        .Font.Size = BTN_frontsize
        ' 设置按钮背景颜色
       ' .BackColor = RGB(220, 220, 220)
    End With
    Set Init_Button = btn
End Function
' 尝试设置控件属性
Private Sub Try_SetProperty(ByVal Ctrl As Object, _
                            ByVal PptyName As String, _
                            ByVal Value As Variant)
    On Error Resume Next
        Err.Number = 0
        Dim tmp As Variant
        tmp = CallByName(Ctrl, PptyName, VbGet)
        If Not Err.Number = 0 Then
            Debug.Print PptyName & ": 获取属性失败(" & Err.Number & ")"
            Exit Sub
        End If
        Select Case TypeName(tmp)
            Case "Empty"
                Exit Sub
            Case "Long"
                Value = CLng(Value)
            Case "Boolean"
                Value = CBool(Value)
            Case "Currency"
                Value = CCur(Value)
        End Select
        If Not Err.Number = 0 Then
            Debug.Print Value & ": 类型转换失败(" & Err.Number & ")"
            Exit Sub
        End If
        Call CallByName(Ctrl, PptyName, VbLet, Value)
        If Not Err.Number = 0 Then
            Debug.Print Value & ": 设置属性失败(" & Err.Number & ")"
            Exit Sub
        End If
    On Error GoTo 0
End Sub
' 获取页面 - 若不存在则创建
Private Function Get_Page(ByVal Pgs As Pages, ByVal Name As String) As Page
    Dim Pg As Page
    On Error Resume Next
        Set Pg = Pgs.item(Name)
    On Error GoTo 0
    If Pg Is Nothing Then
        Set Pg = Pgs.Add(Name, Name, Pgs.Count)
    End If
    Set Get_Page = Pg
End Function
' 产品变化事件处理程序
Private Sub prdObserver_ProductChanged()
 Debug.Print "事件触发"
    UpdateProductInfo
End Sub
' 更新产品信息的方法
Private Sub UpdateProductInfo()
    Dim msg
    Dim mcolor
   mcolor = vbRed
    msg = "产品待选择"
    If Not prdObserver.CurrentProduct Is Nothing Then
          msg = prdObserver.CurrentProduct.PartNumber & "待修改"
            mcolor = vbGreen
    End If
        lblProductInfo.Caption = msg
        lblProductInfo.BackColor = mcolor
End Sub
Private Sub toMP()
    On Error Resume Next
    Dim shell As Object
    Set shell = CreateObject("WScript.Shell")
    shell.Run "https://mp.weixin.qq.com/s?__biz=MzU5MTk1MDUwNg==&mid=2247484525&idx=1&sn=554a37aff4bc876424043a9aa5968d6d&scene=21&poc_token=HCUyg2ijuHYXMx810A5yID4tAYIemJFdJ7FpVvew"
    Set shell = Nothing
    If Err.Number <> 0 Then
        MsgBox "无法公众号链接" & vbCrLf & "错误: " & Err.Description, vbExclamation, "链接错误"
    End If
    On Error GoTo 0
End Sub
Private Sub UserForm_Click()
      toMP
End Sub
Private Sub lblAuthor_Click()
     toMP
End Sub
Private Sub lblProductInfo_Click()
      toMP
End Sub
Private Sub MPgs_MouseDown(ByVal Index As Long, ByVal Button As Integer, ByVal Shift As Integer, ByVal X As Single, ByVal Y As Single)
    If Button <> 1 Then Exit Sub
      If X > Tab_W - 32 Then
      toMP
    End If
End Sub

Attribute VB_Name = "Class_XLM"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private header_bom(1 To 17)
Private header_rv(1 To 14)
Private hdgx(1 To 15)
Private inject_cols
Private extract_cols
Private bom_cols

Private wsEVT  As Ws_Evt
Private wb As Object
Private ws As Object
Private bws As Object

' 在类初始化时检查实例
Private Sub Class_Initialize()

On Error Resume Next
    If gws Is Nothing Then
        Set xlAPP = CreateObject("Excel.Application")
        Set gwb = xlAPP.Workbooks.Add
        Set gws = gwb.ActiveSheet
        Set wb = gwb
        Set ws = gws
        ws.Name = "bom"
    Else
        Set xlAPP = GetObject("Excel.Application")
        Set wb = gwb
        Set ws = gws
    End If
     If Error.Number <> 0 Then
        Err.Clear
'         MsgBox "excel sheet 错误"
'     '    Exit Sub
     End If
    On Error GoTo 0
  xlAPP.Visible = True
    With xlAPP.Windows(1)
        .WindowState = xlNormal
        .Width = 500  ' 设置窗口宽度
        .Height = 1080 ' 设置窗口高度
    End With
'
    xlAPP.Visible = False

    On Error GoTo 0
    Set wsEVT = New Ws_Evt
    wsEVT.Init wb
  iniarr
    
End Sub
Private Sub iniarr()
    inject_cols = Array(1, 3, 5, 7, 13, 9, 14, 11)
    mapping = Array(0, 1, 2, 3, 4, 9, 5, 0, 6, 7, 0, 6, 8, 0, 0, 0)
    'mapping = Array(1, 2, 3, 4, 5, 6, 7, 8, 9, 10, 11, 12, 13, 14, 15, 16)
    
    header_bom(1) = "No." & Chr(10) & "编号"
    header_bom(2) = "Layout" & Chr(10) & "层级"
    header_bom(3) = "PN" & Chr(10) & "零件号"
    header_bom(4) = "Nomenclature" & Chr(10) & "英文名称"
    header_bom(5) = "Definition" & Chr(10) & "中文名称"
    header_bom(6) = "Picture" & Chr(10) & "图像"
    header_bom(7) = "Quantity" & Chr(10) & "数量(PCS)"
    header_bom(8) = "Weight" & Chr(10) & "单质量"
    header_bom(9) = "sum_Weight" & Chr(10) & "总质量"
    header_bom(10) = "Material" & Chr(10) & "材料"
    header_bom(11) = "Thickness" & Chr(10) & "厚度(mm)"
    header_bom(12) = ""
    header_bom(13) = "Material" & Chr(10) & "材料"
    header_bom(14) = "Density" & Chr(10) & "密度(kg/m^3)"
    header_bom(15) = "UTS" & Chr(10) & "抗拉(Mpa)"
    header_bom(16) = "YS" & Chr(10) & "屈服(Mpa)"
    header_bom(17) = "EL" & Chr(10) & "延伸率(%)"
   

    header_rv(1) = "零件号" & Chr(10) & "Partnumber"
    header_rv(2) = "更改" & Chr(10) & "件号"
    header_rv(3) = "英文名称" & Chr(10) & "Nomenclature"
    header_rv(4) = "更改" & Chr(10) & "英文名"
    header_rv(5) = "中文名称" & Chr(10) & "Definition"
    header_rv(6) = "更改" & Chr(10) & "中文名"
    header_rv(7) = "实例名" & Chr(10) & "InstanceName"
    header_rv(8) = "更改" & Chr(10) & "实例名"
    header_rv(9) = "材料" & Chr(10) & "material"
    header_rv(10) = "定义" & Chr(10) & "材料"
    header_rv(11) = "密度" & Chr(10) & "Density"
    header_rv(12) = "更改" & Chr(10) & "密度"
    header_rv(13) = "质量" & Chr(10) & "Mass"
    header_rv(14) = "厚度" & Chr(10) & "Thickness"
    
    hdgx(1) = "NO."
    hdgx(2) = "TIRE"
    hdgx(3) = ""
    hdgx(4) = ""
    hdgx(5) = ""
    hdgx(6) = "PART NO."
    hdgx(7) = "DRAWING NO."
    hdgx(8) = "中文名称"
    hdgx(9) = "ITEM NAME"
    hdgx(10) = "Ver."
    hdgx(11) = "QTY."
    hdgx(12) = "UNIT"
    hdgx(13) = "UNIT WEIGHT"
    hdgx(14) = "TOTAL WEIGHT"
    hdgx(15) = "MATERIAL"
End Sub
Private Sub set_Header(header, idxrow)
    Dim lastCol
    lastCol = UBound(header) - LBound(header) + 1
    With ws
    .Range(.Cells(idxrow, 1), .Cells(idxrow, lastCol)).Value = header
    .Range(.Cells(idxrow, 1), .Cells(idxrow, lastCol)).Interior.color = RGB(190, 190, 190)
    End With
End Sub

Public Sub clear_table()
    ws.UsedRange.ClearContents
End Sub

Public Sub inject_data(rowNb, data)
    ws.Name = "revise prd"
    Dim i As Long
      If ws.Cells(1, 1).Value <> "零件号" & Chr(10) & "Partnumber" Then
        Call set_Header(header_rv, 1)
    End If
    Dim mapdata, osize
    mapdata = Array(0, 1, 2, 3, 4, 5, 6, 7, 8)
    '====获取区域====
    Dim mapcells
        mapcells = Array(0, 1, 3, 5, 7, 9, 11, 13, 14)
    Dim rng As Range
        Set rng = Nothing
    For i = 1 To UBound(mapcells)
            ws.Cells(rowNb, mapcells(i)).Value = data(mapdata(i))
            ws.Cells(rowNb, mapcells(i)).Interior.color = RGB(190, 190, 190)
    Next
    xlAPP.Visible = True
End Sub

Public Sub inject_bom(data)
     ws.Name = "BOM_xx"
    startrow = 2
     Call set_Header(header_bom, startrow - 1)
     lastRow = counter + startrow - 1
     Dim cols
     cols = UBound(data, 2)
     With ws
          ws.Range(.Cells(startrow, 1), .Cells(lastRow, cols)).Value = data
        If lastRow >= 2 Then
            With ws.Range(.Cells(startrow, 9), .Cells(lastRow, 9))
                .Formula = "=G2*H2"  ' G列=第7列，H列=第8列
                .NumberFormat = "0.00"  ' 设置数字格式
            End With
        End If
         End With
     counter = 0
    Call LvMg
    xlAPP.Visible = True
End Sub

Public Sub freesheet()
Set ws = Nothing
Set gws = Nothing
Set gwb = Nothing
Set xlAPP = Nothing
End Sub
 
Public Function extract_data(indRow)
    Dim iCols
    iCols = Array(0, 2, 4, 6, 8, 10, 12)
    Dim temparr As Variant
    temparr = ws.Rows(indRow).Resize(1, 14).Value
    Dim j As Long
    Dim outputArr As Variant
    ReDim outputArr(1 To UBound(iCols))
    For j = 1 To UBound(iCols)
         outputArr(j) = ""
         If IsEmpty(temparr(1, iCols(j))) = False Then
         outputArr(j) = temparr(1, iCols(j))
         End If
    Next
    extract_data = outputArr ' 返回提取的数据
End Function

Private Sub LvMg()
    Dim row_num As Long ' 声明 row_num 变量
    Dim cell ' 声明 cell 变量
'    Set ws = xlApp.ActiveSheet
     With ws
            .Cells.ClearOutline
            .Outline.AutomaticStyles = False
            .Outline.SummaryRow = xlAbove
            .Outline.SummaryColumn = xlRight
    End With
    
    For row_num = 2 To ws.Cells(ws.Rows.Count, 1).End(xlUp).row ' 使用 xlApp.xlUp
        Dim cell_value As Variant
        cell_value = ws.Cells(row_num, 2).Value
        If Not IsEmpty(cell_value) Then
            ws.Rows(row_num).OutlineLevel = cell_value
        End If
    Next
    ' 设置对齐方式和缩进级别
    For Each cell In ws.Range("B2:B" & ws.Cells(ws.Rows.Count, 2).End(xlUp).row) ' 使用 xlApp.xlUp
        If Not IsEmpty(cell) Then
            cell.HorizontalAlignment = xlLeft ' 使用 xlApp.xlLeft
            If IsNumeric(cell.Value) Then
                cell.IndentLevel = cell.Value ' 修改缩进级别与单元格值相等
            End If
        End If
    Next
End Sub

Public Sub LvMg2()
    Dim lastRow, i, LVcol
    With ws
            .Cells.ClearOutline
            .Outline.AutomaticStyles = False
            .Outline.SummaryRow = xlAbove
            .Outline.SummaryColumn = xlRight
            Set LVcol = .Columns(2)
            LVcol.HorizontalAlignment = xlLeft
            lastRow = .Cells(.Rows.Count, 2).End(xlUp).row
            
        For i = 4 To lastRow
            If LVcol.Cells(i).Value <> "" Then
                .Rows(i).OutlineLevel = LVcol.Cells(i).Value ' 设置当前行的大纲级别
                LVcol.Cells(i).IndentLevel = LVcol.Cells(i).Value - 1 ' 设置当前单元格的缩进级别
            End If
        Next
    End With
    lastRow = ws.Cells(Rows.Count, 3).End(xlUp).row
    ws.Rows(lastRow + 3 & ":" & Rows.Count).EntireRow.Hidden = True
    Columns("Q:Q").Select
    Range(Selection, Selection.End(xlToRight)).Select
    Selection.EntireColumn.Hidden = True
End Sub

Public Sub inject_gxbom(data)
     ws.Name = "BOM_xx" & Format(Now, "yymmdd_hhmm")
      startrow = 5
     Call set_Header(hdgx, startrow - 1)
     lastRow = counter + startrow - 1
     Dim cols
     cols = UBound(data, 2)
     With ws
          ws.Range(.Cells(startrow, 1), .Cells(lastRow, cols)).Value = data
        If lastRow >= 5 Then
            With ws.Range(.Cells(startrow, 14), .Cells(lastRow, 14))
                .Formula = "=k5*m5"  ' G列=第7列，H列=第8列
                .NumberFormat = "0.00"  ' 设置数字格式
            End With
        End If
         End With
     counter = 0
 
    xlAPP.Visible = True
End Sub

Attribute VB_Name = "Class_para"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'我是一个对参数对象赋予属性的类
Private pName As String
Private pDesc As String
Private pType As String
Private pStr As Variant
Private pTarget As Object
Private pobj As Object

Private Sub Class_Initialize()
Me.Desc = ""
End Sub
Public Sub Reset()
    Me.Name = ""
    Me.iType = ""
    Me.Str = ""
    Me.Desc = ""
    Set Me.obj = Nothing
    Set Me.Target = Nothing
End Sub
Public Property Get Name() As String
    Name = pName
End Property
Public Property Let Name(ByVal Value As String)
    pName = Value
End Property
Public Property Get iType() As String
    iType = pType
End Property
Public Property Let iType(ByVal Value As String)
    pType = Value
End Property
Public Property Get Desc() As Variant
    Desc = pDesc
End Property
Public Property Let Desc(ByVal Value As Variant)
    pDesc = Value
End Property
Public Property Get Str() As Variant
    Str = pStr
End Property
Public Property Let Str(ByVal Value As Variant)
    pStr = Value
End Property
Public Property Get Target()
   Set Target = pTarget
End Property
Public Property Set Target(Value)
   Set pTarget = Value
End Property

Public Property Get obj()
   Set obj = pobj
End Property
Public Property Set obj(Value)
   Set pobj = Value
End Property
Public Sub SetNT(ByVal newName As String, ByVal newType As String)
    Me.Name = newName
    Me.iType = newType
End Sub

Attribute VB_Name = "KCL"
'Attribute VB_Name = "KCL"
'vba Kantoku_CATVBA_Library ver0.1.0
'KCL.bas - 自定义VBA库
Option Explicit

Private mSW& ' 秒表开始时间

#If VBA7 And Win64 Then
    Private Declare PtrSafe Function timeGetTime Lib "winmm.dll" () As Long
#Else
    Private Declare Function timeGetTime Lib "winmm.dll" () As Long
#End If

' 主程序入口 - 循环选择项目
Sub CATMain()
    Dim msg$: msg = "请选择项目 : 按ESC键退出"
    Dim SI As AnyObject
    Dim doc As Document: Set doc = CATIA.ActiveDocument
    Do
        Set SI = SelectItem(msg)
        If IsNothing(SI) Then Exit Do
        Stop
    Loop
End Sub

'*****CATIA相关函数*****
' 检查是否可以执行操作
''' @param:DocTypes-array(string),string 指定可执行操作的文档类型
''' @return:Boolean
Function CanExecute(ByVal docTypes As Variant) As Boolean
    CanExecute = False
    If CATIA.Windows.Count < 1 Then
        MsgBox "没有打开的窗口"
        Exit Function
    End If
    
    If VarType(docTypes) = vbString Then docTypes = Split(docTypes, ",")
    If Not IsFilterType(docTypes) Then Exit Function
    
    Dim ErrMsg As String
    ErrMsg = "不支持当前活动文档类型。" + vbNewLine + "(" + Join(docTypes, ",") + " 类型除外)"
    
    Dim ActDoc As Document
    On Error Resume Next
        Set ActDoc = CATIA.ActiveDocument
    On Error GoTo 0
    If ActDoc Is Nothing Then
        MsgBox ErrMsg, vbExclamation + vbOKOnly
        Exit Function
    End If
    
    If UBound(filter(docTypes, TypeName(ActDoc))) < 0 Then
        MsgBox ErrMsg, vbExclamation + vbOKOnly
        Exit Function
    End If
    
    CanExecute = True
End Function

' 选择项目
''' @param:Msg-提示信息
''' @param:Filter-array(string),string 选择过滤器(默认为AnyObject)
''' @return:AnyObject
Function SelectItem(ByVal msg$, _
                           Optional ByVal filter As Variant = Empty)
    Dim se As SelectedElement
    Set se = SelectElement(msg, filter)
    
    If IsNothing(se) Then
        Set SelectItem = se
    Else
        Set SelectItem = se.Value
    End If
End Function

' 选择元素
''' @param:Msg-提示信息
''' @param:Filter-array(string),string 选择过滤器(默认为AnyObject)
''' @return:SelectedElement
Function SelectElement(ByVal msg$, _
                           Optional ByVal filter As Variant = Empty) ' _
                           As SelectedElement
    If IsEmpty(filter) Then filter = Array("AnyObject")
    If VarType(filter) = vbString Then filter = ToStrVriAry(filter)
    If Not IsFilterType(filter) Then Exit Function
    
    Dim sel As Variant: Set sel = CATIA.ActiveDocument.Selection
    sel.Clear
    Select Case sel.SelectElement2(filter, msg, False)
        Case "Cancel", "Undo", "Redo"
             Set SelectElement = Nothing
            Exit Function
    End Select
    
    Set SelectElement = sel.item(1)
    sel.Clear
End Function

' 获取内部名称
''' @param:AOj-AnyObject
''' @return:String
Function GetInternalName$(aoj)
    If IsNothing(aoj) Then
        GetInternalName = Empty: Exit Function
    End If
    GetInternalName = aoj.GetItem("ModelElement").InternalName
End Function

' 获取指定类型的父对象
''' @param:anyObj-AnyObject
''' @param:T-String
''' @return:AnyObject
Function GetParent_Of_T( _
    ByVal anyObj As AnyObject, _
    ByVal t As String) _
    As AnyObject
    
    Dim anyObjName As String
    Dim parentName As String
    
    On Error Resume Next
        Set anyObj = asDisp(anyObj)
        anyObjName = anyObj.Name
        parentName = anyObj.Parent.Name
    On Error GoTo 0

    If TypeName(anyObj) = TypeName(anyObj.Parent) And _
       anyObjName = parentName Then
        Set GetParent_Of_T = Nothing
        Exit Function
    End If
    If TypeName(anyObj) = t Then
        Set GetParent_Of_T = anyObj
    Else
        Set GetParent_Of_T = GetParent_Of_T(anyObj.Parent, t)
    End If
End Function

Private Function asDisp(o As INFITF.CATBaseDispatch) As INFITF.CATBaseDispatch
    Set asDisp = o
End Function

' 获取Brep名称
''' @param:MyBRepName-String
''' @return:String
Function GetBrepName(MyBRepName As String) As String
    MyBRepName = Replace(MyBRepName, "Selection_", "")
    MyBRepName = Left(MyBRepName, InStrRev(MyBRepName, "));"))
    MyBRepName = MyBRepName + ");WithPermanentBody;WithoutBuildError;WithSelectingFeatureSupport;MFBRepVersion_CXR15)"
    GetBrepName = MyBRepName
End Function

' 获取语言
'return-ISO 639-1 code
'https://ja.wikipedia.org/wiki/ISO_639-1%E3%82%B3%E3%83%BC%E3%83%89%E4%B8%80%E8%A6%A7
Function GetLanguage() As String
    GetLanguage = "non"
    If CATIA.Windows.Count < 1 Then Exit Function
    GetLanguage = "other"
    CATIA.ActiveDocument.Selection.Clear
    Dim st As String: st = CATIA.StatusBar
    Select Case True
        Case ExistsKey(st, "object")
            ' 英文-Select an object or a command
            GetLanguage = "en"
        Case ExistsKey(st, "objet")
            ' 法语-选择一个对象或命令
            GetLanguage = "fr"
        Case ExistsKey(st, "Objekt")
            ' 德语-选择一个对象或命令
            GetLanguage = "de"
        Case ExistsKey(st, "oggetto")
            ' 意大利语-选择一个对象或命令
            GetLanguage = "it"
        Case ExistsKey(st, "命令")
            ' 日语-选择一个命令或对象
            GetLanguage = "ja"
        Case ExistsKey(st, "объект")
            ' 俄语-选择一个对象或命令
            GetLanguage = "ru"
        Case ExistsKey(st, "对象")
            ' 中文-选择一个对象或命令
            GetLanguage = "zh"
        Case Else
            Select Case Len(st)
                Case 13
                    ' 韩语-???? ?? ?? ??@unicode编码示例
                    GetLanguage = "ko"
                Case 23
                    ' 日语-日语长提示示例
                    GetLanguage = "ja"
                Case Else
                    ' 其他情况
            End Select
    End Select
End Function
' 检查是否为字符串数组
Private Function IsStringAry(ByVal ary As Variant) As Boolean
    IsStringAry = False
    If Not IsArray(ary) Then Exit Function
    Dim i&
    For i = 0 To UBound(ary)
        If Not VarType(ary(i)) = vbString Then Exit Function
    Next
    IsStringAry = True
End Function

' 检查过滤器类型是否有效
Private Function IsFilterType(ByVal ary As Variant) As Boolean
    IsFilterType = False
    Dim ErrMsg$: ErrMsg = "过滤器类型无效" + vbNewLine + _
                          "需要为Variant(String)类型的数组" + vbNewLine + _
                          "(具体请参考文档)"
    If Not IsStringAry(ary) Then
        MsgBox ErrMsg
        Exit Function
    End If
    IsFilterType = True
End Function

' 将字符串转换为变体数组
Private Function ToStrVriAry(ByVal S$) As Variant
    Dim ary As Variant: ary = Split(S, ",")
    Dim vriary() As Variant: ReDim vriary(UBound(ary))
    Dim i&
    For i = 0 To UBound(ary)
        vriary(i) = ary(i)
    Next
    ToStrVriAry = vriary
End Function

'*****通用相关函数*****
' 检查对象是否为Nothing
''' @param:OJ-Variant(Of Object)
''' @return:Boolean
Function IsNothing(ByVal oj As Variant) As Boolean
    IsNothing = oj Is Nothing
End Function

' 创建Scripting.Dictionary对象
''' @param:CompareMode-Long
''' @return:Object(Of Dictionary)
Function InitDic(Optional CompareMode As Long = vbBinaryCompare) As Object
    Dim Dic As Object
    Set Dic = CreateObject("Scripting.Dictionary")
    Dic.CompareMode = CompareMode
    Set InitDic = Dic
End Function

' 创建ArrayList对象
''' @return:Object(Of ArrayList)Public
Function InitLst() As Object
    Set InitLst = CreateObject("System.Collections.ArrayList")
End Function

' 检查对象是否为指定类型
''' @param:OJ-Object
''' @param:T-String
''' @return:Boolean
Function IsType_Of_T(ByVal oj As Object, ByVal t$) As Boolean
    IsType_Of_T = IIf(TypeName(oj) = t, True, False)
'    MsgBox TypeName(oj)
End Function


'*****数组相关函数*****
' 合并两个数组
''' @param:Ary1-Variant(Of Array)
''' @param:Ary2-Variant(Of Array)
''' @return:Variant(Of Array)
Function JoinAry(ByVal Ary1 As Variant, ByVal Ary2 As Variant)
    Select Case True
        Case Not IsArray(Ary1) And Not IsArray(Ary2)
            JoinAry = Empty: Exit Function
        Case Not IsArray(Ary1)
            JoinAry = Ary2: Exit Function
        Case Not IsArray(Ary2)
            JoinAry = Ary1: Exit Function
    End Select
    Dim StCount&: StCount = UBound(Ary1)
    ReDim Preserve Ary1(UBound(Ary1) + UBound(Ary2) + 1)
    Dim i&
    If IsObject(Ary2(0)) Then
        For i = StCount + 1 To UBound(Ary1)
            Set Ary1(i) = Ary2(i - StCount - 1)
        Next
    Else
        For i = StCount + 1 To UBound(Ary1)
            Ary1(i) = Ary2(i - StCount - 1)
        Next
    End If
    JoinAry = Ary1
End Function

' 获取数组指定范围的元素
''' @param:Ary-Variant(Of Array)
''' @param:StartIdx-Long
''' @param:EndIdx-Long
''' @return:Variant(Of Array)
Function GetRangeAry(ByVal ary As Variant, ByVal StartIdx&, ByVal EndIdx&) As Variant
    If Not IsArray(ary) Then Exit Function
    If EndIdx - StartIdx < 0 Then Exit Function
    If StartIdx < 0 Then Exit Function
    If EndIdx > UBound(ary) Then Exit Function
    
    Dim RngAry() As Variant: ReDim RngAry(EndIdx - StartIdx)
    Dim i&
    For i = StartIdx To EndIdx
        RngAry(i - StartIdx) = ary(i)
    Next
    GetRangeAry = RngAry
End Function

' 克隆数组
''' @param:Ary-Variant(Of Array)
''' @return:Variant(Of Array)
Function CloneAry(ByVal ary As Variant) As Variant
    If Not IsArray(ary) Then Exit Function
    CloneAry = GetRangeAry(ary, 0, UBound(ary))
End Function

' 检查两个数组是否相等
''' @param:Ary1-Variant(Of Array)
''' @param:Ary2-Variant(Of Array)
''' @return:Boolean
Function IsAryEqual(ByVal Ary1 As Variant, ByVal Ary2 As Variant) As Boolean
    IsAryEqual = False
    If Not IsArray(Ary1) Or Not IsArray(Ary2) Then Exit Function
    If Not UBound(Ary1) = UBound(Ary2) Then Exit Function
    Dim i&
    For i = 0 To UBound(Ary1)
        If Not Ary1(i) = Ary2(i) Then Exit Function
    Next
    IsAryEqual = True
End Function


'*****IO相关函数*****
' 获取FileSystemObject对象
''' @return:Object(Of FileSystemObject)
Function GetFSO() As Object
    Set GetFSO = CreateObject("Scripting.FileSystemObject")
End Function

' 分割路径名
''' @param:FullPath-完整路径
''' @return:Variant(Of Array(Of String)) (0-路径 1-文件名 2-扩展名)
Function SplitPathName(ByVal FullPath$) As Variant
    Dim path(2) As String
    With GetFSO
        path(0) = .GetParentFolderName(FullPath)
        path(1) = .GetBaseName(FullPath)
        path(2) = .GetExtensionName(FullPath)
    End With
    SplitPathName = path
End Function

' 合并路径名
''' @param:Path-Variant(Of Array(Of String)) (0-路径 1-文件名 2-扩展名)
''' @return:完整路径
Function JoinPathName$(ByVal path As Variant)
    If Not IsArray(path) Then Stop ' 输入错误
    If Not UBound(path) = 2 Then Stop ' 输入错误
    JoinPathName = path(0) + "\" + path(1) + "." + path(2)
End Function

' 检查路径是否存在
''' @param:Path-路径
''' @return:Boolean
Function isExists(ByVal path$) As Boolean
    isExists = False
    Dim fso As Object: Set fso = GetFSO
    If fso.FileExists(path) Then
        isExists = True: Exit Function ' 文件
    ElseIf fso.FolderExists(path) Then
        isExists = True: Exit Function ' 文件夹
    End If
    Set fso = Nothing
End Function
Function DeleteMe(ByVal path$) As Boolean
    DeleteMe = False
    On Error Resume Next
    Dim fso As Object: Set fso = GetFSO
    If fso.FileExists(path) Then
        fso.DeleteFile path, True
    End If
    If Error.Number = 0 Then
        DeleteMe = True
    Else
    Error.Clear
    End If
    Set fso = Nothing
End Function
' 获取新文件名
''' @param:Path-完整路径
''' @return:新的完整路径
Function GetNewName$(ByVal oldPath$)
    Dim path As Variant
    path = SplitPathName(oldPath)
    path(2) = "." & path(2)
    Dim newPath$: newPath = path(0) + "\" + path(1)
    If Not isExists(newPath + path(2)) Then
        GetNewName = newPath + path(2)
        Exit Function
    End If
    Dim TempName$, i&: i = 0
    Do
        i = i + 1
        TempName = newPath + "_" + CStr(i) + path(2)
        If Not isExists(TempName) Then
            GetNewName = TempName
            Exit Function
        End If
    Loop
End Function

' 写入文件
''' @param:Path-完整路径
''' @param:Txt-String
Sub WriteFile(ByVal path$, ByVal txt) '$)
    On Error Resume Next
        Call GetFSO.OpenTextFile(path, 2, True).Write(txt)
    On Error GoTo 0
End Sub

' 读取文件
''' @param:Path-完整路径
''' @return:Variant(Of Array(Of String))
Function ReadFile(ByVal path$) As Variant
    On Error Resume Next
    With GetFSO.GetFile(path).OpenAsTextStream
        ReadFile = Split(.ReadAll, vbNewLine)
        .Close
    End With
    On Error GoTo 0
End Function


'*****计时相关函数*****
' 启动秒表
Sub SW_Start()
    mSW = timeGetTime
End Sub

' 获取计时时间
''' @return:Double(Unit:s)
Function SW_GetTime#()
    SW_GetTime = IIf(mSW = 0, -1, (timeGetTime - mSW) * 0.001)
End Function

Public Function GetInput(msg) As String
    Dim UserInput As String
    UserInput = InputBox(msg, "输入提示")
    ' 如果用户没有输入或点击取消，则返回默认值"XX"
    If UserInput = "" Or UserInput = "0" Then
        GetInput = ""
    Else
        GetInput = UserInput
    End If
End Function

'@@param: oPath-路径
Public Function ofParentPath(ByVal opath$)
    Dim idx
    idx = InStrRev(opath, "\")
If idx > 0 Then
        ofParentPath = Left(opath, idx)
    Else
        ofParentPath = opath
    End If
End Function
' 检查字符串中是否包含指定关键字
' 忽略大小写进行检查
Public Function ExistsKey(ByVal txt As String, ByVal Key As String) As Boolean
    ExistsKey = IIf(InStr(LCase(txt), LCase(Key)) > 0, True, False)
End Function
'@@ param:ostr-时间格式

Public Function timestamp(Optional ByVal ostr) As String
    Dim FT As String  ' 显式声明变量
    Select Case True
        Case ExistsKey(ostr, "i"): FT = "yymmdd.hhnn"
        Case ExistsKey(ostr, "h"): FT = "yymmdd.hh"
        Case ExistsKey(ostr, "d"): FT = "yymmdd"
        Case ExistsKey(ostr, "s"): FT = "yymmdd.hhnnss"
        Case Else: FT = "yymmdd"  ' 默认格式，避免未赋值情况
    End Select
    timestamp = Format(Now, FT)
End Function
Function isEngPath(ByVal path As String) As Boolean
    Dim i As Long, charCode As Long
    Dim validChars As String
    ' 定义允许的英文符号（包括路径分隔符）
    validChars = "!@#$%^&*()-_=+[]{};:'"",.<>/?\|~\/"
    ' 遍历路径中的每个字符
    For i = 1 To Len(path)
        charCode = AscW(Mid(path, i, 1))
        ' 检查是否为英文字母（A-Z, a-z）
        If (charCode >= 65 And charCode <= 90) Or _
           (charCode >= 97 And charCode <= 122) Then
            GoTo NextChar  ' 等同于 Continue For
        End If
        ' 检查是否为数字（0-9）
        If charCode >= 48 And charCode <= 57 Then
            GoTo NextChar  ' 等同于 Continue For
        End If
        ' 检查是否为允许的英文符号
        If InStr(validChars, Mid(path, i, 1)) > 0 Then
            GoTo NextChar  ' 等同于 Continue For
        End If
        ' 如果都不是，则路径包含非法字符
        isEngPath = False
        Exit Function
NextChar:
    Next i
    
    ' 所有字符都通过检查
    isEngPath = True
End Function

' 此函数用于检查输入的路径是否包含中文字符
' 参数:
'   pathToCheck - 需要检查的路径
' 返回值:
'   Boolean 类型，True 表示路径包含中文，False 表示不包含
Function isPathchn(pathToCheck) As Boolean
    Dim regEx As Object
    Set regEx = CreateObject("VBScript.RegExp")
    
    ' 设置正则表达式模式，匹配中文字符
    regEx.Pattern = "[\u4e00-\u9fa5]"
    regEx.IgnoreCase = True
    regEx.Global = True
    ' 执行匹配并返回结果
    isPathchn = regEx.test(pathToCheck)
    Set regEx = Nothing
End Function
'@iStr string
'获得字符串最后一个"iext"之前的字符或返回原字符
Function strbflast(Str, iext)
Dim idx
idx = InStrRev(Str, iext)
If idx > 0 Then
        strbflast = Left(Str, idx)
    Else
        strbflast = Str
    End If
End Function

'@iStr string
'获得字符串第一个"_"之前的字符或返回原字符
Function strbf1st(iStr, iext)
    Dim oPrefix
        Dim underscorePos As Long
        underscorePos = InStr(iStr, iext)
        If underscorePos > 0 Then
            oPrefix = Left(iStr, underscorePos - 1)
        Else
           oPrefix = iStr
        End If
        strbf1st = oPrefix
End Function
 
Function straf1st(iStr, iext)
Dim idx
idx = InStr(iStr, iext)
If idx > 0 Then
        straf1st = Mid(iStr, idx)
    Else
        straf1st = iStr
    End If
End Function

Attribute VB_Name = "M25_Holecenter"
'Attribute VB_Name = "M25_Holecenter"
' 获得识别特征下的所有孔中心
'{GP:2}
'{EP:ctrhole}
'{Caption:get孔中心点}
'{ControlTipText: 提示选择实体后导出所有孔中心，必须是识别孔特征后的实体}
'{BackColor:12648447}

Sub ctrhole()

 If CATIA.Windows.Count < 1 Then
        MsgBox "没有打开的窗口"
        Exit Sub
    End If
    
  If Not CanExecute("PartDocument") Then Exit Sub

    Set oDoc = CATIA.ActiveDocument
    Set oPart = oDoc.part
    Set HSF = oPart.HybridShapeFactory
    '======= 要求选择body
    Dim imsg, filter(0)
    imsg = "请选择body"
    filter(0) = "Body"
    Dim obdy
    Set obdy = KCL.SelectElement(imsg, filter).Value
    Set targethb = oPart.HybridBodies.Add()
    targethb.Name = "extracted points"
    If Not obdy Is Nothing Then
            Set holeBody = obdy
            For Each Hole In holeBody.Shapes
            If TypeOf Hole Is Hole Then
                Set skt = Hole.Sketch
                Set Pt = HSF.AddNewPointCoord(0, 0, 0)
                Set ref = oPart.CreateReferenceFromObject(skt)
                Pt.PtRef = ref
                Pt.Name = "Pt_" & i
                targethb.AppendHybridShape Pt
                oPart.InWorkObject = Pt
                oPart.Update
                i = i + 1
            End If
        Next
        MsgBox "完成：" & i & "个点", vbInformation
    End If
End Sub

Attribute VB_Name = "M31_NewPN"
'Attribute VB_Name = "m30_NewPn"
'{GP:3}
'{Ep:CATMain}
'{Caption:项目前缀}
'{ControlTipText:为所有零件号增加项目前缀}
'{BackColor:}

Private prj
Sub CATMain()

If Not KCL.CanExecute("ProductDocument") Then Exit Sub
Set rootprd = CATIA.ActiveDocument.Product
If Not rootprd Is Nothing Then
 Dim imsg
          imsg = "请输入你的项目名称"
        prj = KCL.GetInput(imsg)
        If prj = "" Then
            Exit Sub
        End If
    Call rePn(rootprd)
Else
 Exit Sub
End If
End Sub

Sub rePn(oprd)
    pn = oprd.PartNumber
    purePN = KCL.straf1st(pn, "_")
    oprd.PartNumber = prj & "_" & purePN
    For Each Product In oprd.Products
        Call rePn(Product)
        Next
End Sub

Attribute VB_Name = "M31_NewPN2"
'Attribute VB_Name = "m30_NewPn2"
'{GP:111}
'{Ep:CATMain}
'{Caption:件号后缀}
'{ControlTipText:为所有零件号增加项目前缀}
'{BackColor:}
Private oSuffix
Sub CATMain()
If Not KCL.CanExecute("ProductDocument") Then Exit Sub
    If pdm Is Nothing Then
        Set pdm = New class_PDM
    End If
    Set oprd = pdm.selPrd()
    If oprd Is Nothing Then
        MsgBox "没有选择产品"
    Else
        Dim imsg
              imsg = "请输入后缀"
            oSuffix = KCL.GetInput(imsg)
            If oSuffix = "" Then
                Exit Sub
            End If
        Call postPn(oprd)
    End If
End Sub

Sub postPn(oprd)
    pn = oprd.PartNumber
    oprd.PartNumber = pn & "_" & oSuffix
    For Each Product In oprd.Products
        Call postPn(Product)
        Next
End Sub

Attribute VB_Name = "M60_Color"
'Attribute VB_Name = "M60_Color"
'{GP:6}
'{Ep:CATmain}
'{Caption:背景颜色}
'{ControlTipText:白黑色背景切换}
'{BackColor: }
Const CF_BITMAP = 2
' 更新按钮文字的公共函数
Public Sub UpdateButtonText(ByVal btn As MSForms.CommandButton, ByVal isWhiteBackground As Boolean)
    If isWhiteBackground Then
        btn.Caption = "默认背景"
    Else
        btn.Caption = "白色背景"
    End If
End Sub

Sub CATMain()
    On Error GoTo ErrorHandler
        If CATIA.activeWindow.Count = 0 Then
            Err.Raise 1001, , "未检测到打开的CATIA文档"
            Exit Sub
        End If
         Dim oWindow, oViewer
        Set oWindow = CATIA.activeWindow
        Set oViewer = oWindow.ActiveViewer
    On Error GoTo 0
    oWindow.Layout = catWindowGeomOnly
    oViewer.Reframe
    Dim MyViewer: Set MyViewer = CATIA.activeWindow.ActiveViewer
    Dim currentColor(2)
    MyViewer.GetBackgroundColor currentColor
    ' 根据当前背景色直接切换
    If currentColor(0) = 1 And currentColor(1) = 1 And currentColor(2) = 1 Then
        ' 当前是白色背景，切换到默认背景
        MyViewer.PutBackgroundColor Array(0.2, 0.2, 0.4)
        oWindow.Layout = catWindowSpecsAndGeom
    Else
        ' 当前是默认背景，切换到白色背景
        MyViewer.PutBackgroundColor Array(1, 1, 1)
        oWindow.Layout = catWindowGeomOnly
    End If
ErrorHandler:
    If Err.Number <> 0 Then
        Select Case Err.Number
            Case 1001
                MsgBox "CATIA 错误：" & Err.Description, vbCritical
                Err.Clear
                Exit Sub
            Case 1002
        End Select
    End If
End Sub

Attribute VB_Name = "M61_capture"
'Attribute VB_Name = "mCaptureClipboard"
'{GP:64}
'{Ep:CaptureToClipboard}
'{Caption:截图到剪贴板}
'{ControlTipText:将当前CATIA视图截图复制到剪贴板}
'{BackColor:16744703}


' 需要声明Windows API函数
'#If VBA7 Then
'    Private Declare PtrSafe Function OpenClipboard Lib "user32" (ByVal hwnd As LongPtr) As LongPtr
'    Private Declare PtrSafe Function EmptyClipboard Lib "user32" () As LongPtr
'    Private Declare PtrSafe Function CloseClipboard Lib "user32" () As LongPtr
'    Private Declare PtrSafe Function SetClipboardData Lib "user32" (ByVal wFormat As Long, ByVal hMem As LongPtr) As LongPtr
'    Private Declare PtrSafe Function CopyImage Lib "user32" (ByVal handle As LongPtr, ByVal un1 As Long, ByVal n1 As Long, ByVal n2 As Long, ByVal un2 As Long) As LongPtr
'    Private Declare PtrSafe Function LoadImage Lib "user32" Alias "LoadImageA" (ByVal hInst As LongPtr, ByVal lpsz As String, ByVal un1 As Long, ByVal n1 As Long, ByVal n2 As Long, ByVal un2 As Long) As LongPtr
'#Else
'    Private Declare Function OpenClipboard Lib "user32" (ByVal hwnd As Long) As Long
'    Private Declare Function EmptyClipboard Lib "user32" () As Long
'    Private Declare Function CloseClipboard Lib "user32" () As Long
'    Private Declare Function SetClipboardData Lib "user32" (ByVal wFormat As Long, ByVal hMem As Long) As Long
'    Private Declare Function CopyImage Lib "user32" (ByVal handle As Long, ByVal un1 As Long, ByVal n1 As Long, ByVal n2 As Long, ByVal un2 As Long) As Long
'    Private Declare Function LoadImage Lib "user32" Alias "LoadImageA" (ByVal hInst As Long, ByVal lpsz As String, ByVal un1 As Long, ByVal n1 As Long, ByVal n2 As Long, ByVal un2 As Long) As Long
'#End If

Const CF_BITMAP = 2

Sub CaptureToClipboard()

MsgBox "没编呢"
'    On Error GoTo ErrorHandler
'
'    ' 获取CATIA应用和活动窗口
'    Dim catia As Application
'    Set catia = catia
'
'    If catia.ActiveWindow Is Nothing Then
'        MsgBox "没有活动窗口可截图", vbExclamation
'        Exit Sub
'    End If
'
'    ' 获取当前视图
'    Dim viewer As viewer
'    Set viewer = catia.ActiveWindow.ActiveViewer
'
'    ' 临时文件路径
'    Dim tempFile As String
'    tempFile = Environ("TEMP") & "\CATIA_temp_capture.bmp"
'
'    ' 先保存为临时BMP文件
'    viewer.CaptureToFile 0, tempFile ' 0 = catCaptureFormatBMP
'
'    ' 将BMP文件复制到剪贴板
'    Dim hBitmap As Long
'    hBitmap = LoadImage(0, tempFile, 0, 0, 0, &H10) ' LR_LOADFROMFILE
'
'    If hBitmap <> 0 Then
'        OpenClipboard 0
'        EmptyClipboard
'        SetClipboardData CF_BITMAP, hBitmap
'        CloseClipboard
'        MsgBox "截图已复制到剪贴板", vbInformation
'    Else
'        MsgBox "无法将图像复制到剪贴板", vbExclamation
'    End If
'
'    ' 删除临时文件
'    Kill tempFile
'
'    Exit Sub
'
'ErrorHandler:
'    MsgBox "截图失败：" & Err.Description, vbCritical
End Sub


Function PictureGet(PartName As String, oprd) As String
    Dim ObjViewer3D As Viewer3D
    Set ObjViewer3D = CATIA.activeWindow.ActiveViewer
    
    Dim objCamera3D As Camera3D
    Set objCamera3D = CATIA.ActiveDocument.Cameras.item(1)
    
    If PartName = "" Then
        MsgBox "No name was entered. Operation aborted.", vbExclamation, "Cancel"
    Else
        'turn off the spec tree
        Dim objSpecWindow As SpecsAndGeomWindow
        Set objSpecWindow = CATIA.activeWindow
        objSpecWindow.Layout = catWindowGeomOnly
        
        '=== 新增: 聚焦到当前组件 ===
        CATIA.ActiveDocument.Selection.Clear
        CATIA.ActiveDocument.Selection.Add oprd
        ObjViewer3D.Reframe ' 这将使视图聚焦到选中的组件
        '=========================
        
        'Toggle Compass
        CATIA.StartCommand ("Compass")
        
        'change background color to white
        Dim DBLBackArray(2)
        ObjViewer3D.GetBackgroundColor (DBLBackArray)
        Dim dblWhiteArray(2)
        dblWhiteArray(0) = 1
        dblWhiteArray(1) = 1
        dblWhiteArray(2) = 1
        ObjViewer3D.PutBackgroundColor (dblWhiteArray)
        
        'file location to save image
        Dim fileloc As String
        fileloc = "C:\Temp\"
        
        Dim exten As String
        exten = ".jpg"
        
        Dim strName As String
        strName = fileloc & PartName & exten
        
        'clear selection for picture
        CATIA.ActiveDocument.Selection.Clear()
        
        'increase to fullscreen to obtain maximum resolution
        ObjViewer3D.FullScreen = True
        
        'take picture
        ObjViewer3D.CaptureToFile 4, strName
        
        '*******************RESET**********************
        ObjViewer3D.FullScreen = False
        ObjViewer3D.PutBackgroundColor (DBLBackArray)
        objSpecWindow.Layout = catWindowSpecsAndGeom
        CATIA.StartCommand ("Compass")
    End If
End Function

Attribute VB_Name = "Module2"
Sub DRA()
Set oDoc = CATIA.ActiveDocument
Set oShts = oDoc.Sheets
k = oShts.Count
i = 5
    Dim oSHT As DrawingSheet
    Set oSHT = oShts.item(i)
    oSHT.Activate
        oo = straf1st(oSHT.Name, " ")
        oSHT.Name = "SH" & i & oo
    Set oviews = oSHT.Views
    Set oView = oviews.item("Background View")
   oView.Activate
    Set ots = oView.Texts
    Set Pg = ots.GetItem("gongxxzhang")
    Pg.Text = "共" & k - 1 & "页"
      oView.SaveEdition
    Set Pg = ots.GetItem("dixxzhang")
    Pg.Text = "第" & i & "页"
    oView.SaveEdition
End Sub

Attribute VB_Name = "Module3"
Sub pgupdate()
Set oDoc = CATIA.ActiveDocument
Set oShts = oDoc.Sheets
k = oShts.Count
On Error Resume Next
i = 1
For i = 1 To oShts.Count
    Dim oSHT As DrawingSheet
    Set oSHT = oShts.item(i)
    oSHT.Activate
        oo = straf1st(oSHT.Name, " ")
        oSHT.Name = "SH" & i & oo
    Set oviews = oSHT.Views
    Set oView = oviews.item("Background View")
    Set ots = oView.Texts
    Set Pg = ots.GetItem("dixxzhang")
    Pg.Text = "第" & i & "页"
Set Pg = ots.GetItem("gongxxzhang")

  Pg.Text = "共" & k - 1 & "页"
Next
On Error GoTo 0
End Sub

Attribute VB_Name = "Module6"
'Private Declare PtrSafe Function OpenClipboard Lib "user32" (ByVal hwnd As LongPtr) As Long
'Private Declare PtrSafe Function EmptyClipboard Lib "user32" () As Long
'Private Declare PtrSafe Function CloseClipboard Lib "user32" () As Long
'Private Declare PtrSafe Function SetClipboardData Lib "user32" (ByVal wFormat As Long, ByVal hMem As LongPtr) As LongPtr
'Sub main()
'
'
'Call CaptureAndCopyToClipboard
'End Sub
'Public Sub CaptureAndCopyToClipboard()
'    Dim CATIA As Object
'    Dim activeWindow As Object
'    Dim tempFilePath As String
'
'    ' 获取CATIA应用程序实例
'    Set CATIA = GetObject(, "CATIA.Application")
'    Set activeWindow = CATIA.activeWindow
'
'    ' 临时文件路径
'    tempFilePath = Environ$("TEMP") & "\temp_screenshot.png"
'
'    ' 捕获活动窗口截图
'    activeWindow.ActiveViewer.CaptureToFile tempFilePath, 0, True ' 0表示PNG格式
'
'    ' 复制到剪贴板
'    CopyImageToClipboard tempFilePath
'
'    ' 清理
'    Kill tempFilePath
'
'    Set activeWindow = Nothing
'    Set CATIA = Nothing
'End Sub
'
'Private Sub CopyImageToClipboard(ByVal imagePath As String)
'    ' 使用Windows Script Host创建Shell应用程序对象
'    Dim objShell As Object
'    Set objShell = CreateObject("WScript.Shell")
'
'    ' 使用PowerShell命令复制图片到剪贴板
'    Dim psCommand As String
'    psCommand = "powershell -command ""Add-Type -AssemblyName System.Windows.Forms; [System.Windows.Forms.Clipboard]::SetImage([System.Drawing.Image]::FromFile('"" & imagePath & ""'))"""
'
'    objShell.Run psCommand, 0, True
'
'    Set objShell = Nothing
'End Sub

Attribute VB_Name = "Module7"
Private Sub cmdExecute_Click()
    Dim updateDate As Boolean
    Dim updatePath As Boolean
    Dim dateValue As String
    updateDate = chkDate.Value
    updatePath = chkPath.Value
    
    
    If updateDate Then
        If Trim(txtDate.Text) = "" Then
            MsgBox "?", vbExclamation, "日期"
            txtDate.SetFocus
            Exit Sub
        End If
        
        dateValue = txtDate.Text
        MsgBox "灏嗘洿鏂版棩鏈熶负: " & dateValue, vbInformation, "淇℃伅"
    End If
    
    ExecuteOperations updateDate, updatePath, dateValue
End Sub

Private Sub ExecuteOperations(needUpdateDate As Boolean, needUpdatePath As Boolean, newDate As String)
    Dim resultMsg As String
    resultMsg = "鎿嶄綔缁撴灉:" & vbCrLf & vbCrLf
    
    If needUpdateDate Then
        resultMsg = resultMsg & "1. 宸叉洿鏂版棩鏈熶负: " & newDate & vbCrLf
        ' UpdateDateFunction(newDate)
    Else
        resultMsg = resultMsg & "1. 鏈�鏇存柊鏃ユ�?" & vbCrLf
    End If
    
    If needUpdatePath Then
        resultMsg = resultMsg & "2. 宸叉洿鏂拌矾寰?" & vbCrLf
        ' UpdatePathFunction()
    Else
        resultMsg = resultMsg & "2. 鏈�鏇存柊璺�寰?" & vbCrLf
    End If
    
    MsgBox resultMsg, vbInformation, "鎿嶄綔瀹屾垚"
End Sub

Private Sub chkDate_Click()
    txtDate.Enabled = chkDate.Value
    If chkDate.Value Then
        txtDate.SetFocus
    End If
End Sub

Private Sub UserForm_Initialize()
    txtDate.Enabled = False
    txtDate.Text = "YYYY-MM-DD"
End Sub

Attribute VB_Name = "ProductObserver"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'VERSION 1.0 CLASS
'BEGIN
'  MultiUse = -1  'True
'End
'Attribute VB_Name = "ProductObserver"
'Attribute VB_GlobalNameSpace = False
'Attribute VB_Creatable = False
'Attribute VB_PredeclaredId = False
'Attribute VB_Exposed = False
Option Explicit

' 事件声明
Public Event ProductChanged()

' 私有变量存储当前产品
Private mProduct As Object

' 属性：当前产品
Public Property Get CurrentProduct() As Object
    Set CurrentProduct = mProduct
End Property

Public Property Set CurrentProduct(ByVal newProduct As Object)
    ' 设置新产品并触发事件
    Set mProduct = newProduct
    RaiseEvent ProductChanged
End Property

' 初始化
Private Sub Class_Initialize()
    Set mProduct = Nothing
End Sub

' 清理
Private Sub Class_Terminate()
    Set mProduct = Nothing
End Sub

Attribute VB_Name = "Ws_Evt"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private WithEvents pWb As Workbook
Attribute pWb.VB_VarHelpID = -1
Public Sub Init(wbInstance)
    Set pWb = wbInstance
End Sub
Private Sub pWb_BeforeClose(Cancel As Boolean)
    ' 清除实例并释放对象
    Set gwb = Nothing
    Set gws = Nothing
    Set xlAPP = Nothing
End Sub

Attribute VB_Name = "askdir"
Attribute VB_Base = "0{32F1C657-EAA1-45FD-BDEF-6FFFADCECC0B}{BA01A4B8-4AFD-4364-8AB0-B9FB4C246478}"
Attribute VB_GlobalNameSpace = False
Attribute VB_Creatable = False
Attribute VB_PredeclaredId = True
Attribute VB_Exposed = False
Attribute VB_TemplateDerived = False
Attribute VB_Customizable = False
'VERSION 1.0 CLASS
'Begin
'  MultiUse = -1  'True
'End

Private Const itemgap = 3
Private Const fmargin = 6
Private Const bmargin = 6
' Use WithEvents to handle events for dynamically created controls.
Private WithEvents chk_TM As MSForms.CheckBox
Attribute chk_TM.VB_VarHelpID = -1
Private WithEvents chk_Path As MSForms.CheckBox
Attribute chk_Path.VB_VarHelpID = -1
Private WithEvents cmdOK As MSForms.CommandButton
Attribute cmdOK.VB_VarHelpID = -1
Private WithEvents cmdCancel As MSForms.CommandButton
Attribute cmdCancel.VB_VarHelpID = -1
Private WithEvents txt_TM As MSForms.TextBox
Attribute txt_TM.VB_VarHelpID = -1
Private colls As New collection
Private class_ctrl As clsCtrls

Private Sub UserForm_Initialize()
    ' 设置窗体基本属性
    Me.Caption = "零件号更新和路径选择"
    Me.Width = 300
    Me.Height = 130
    Me.StartUpPosition = 1
   
    Set chk_TM = Me.Controls.Add("Forms.CheckBox.1", "cjk", True)
        With chk_TM
            .Name = "chk_TM"
            .Caption = "是否更新CATIA零件号时间戳"
            .Left = fmargin
            .Top = fmargin
            .Width = 250
            .Height = 20
        End With
        
    Set class_ctrl = New clsCtrls
    
    Set txt_TM = Me.Controls.Add("Forms.TextBox.1", "txt_TM", True)
    
        With txt_TM
            .Enabled = False
            .Left = fmargin + 20
            .Top = chk_TM.Top + chk_TM.Height + itemgap
            .Width = 240
            .Height = 20
        End With
    
     Set class_ctrl.txt = txt_TM
    class_ctrl.ohint = "请输入日期格式，日=d或day，时=hour或h，分=min或i，默认为日"
    
    txt_TM.Text = class_ctrl.ohint
    txt_TM.ForeColor = &H808080
    
    colls.Add class_ctrl
    
    Set chk_Path = Me.Controls.Add("Forms.CheckBox.1")
        With chk_Path
            .Name = "chk_Path"
            .Caption = "是否导出到当前路径"
            .Left = fmargin
            .Top = txt_TM.Top + txt_TM.Height + itemgap
            .Width = 150
            .Height = 20
        End With
        
    Set cmdOK = Me.Controls.Add("Forms.CommandButton.1")
        With cmdOK
            .Name = "cmdOK"
            .Caption = "确定"
            .Left = (Me.InsideWidth - (80 * 2) - itemgap) / 2
            .Top = chk_Path.Top + 20
            .Width = 60
            .Height = 25
        End With
    
    Set cmdCancel = Me.Controls.Add("Forms.CommandButton.1")
        With cmdCancel
            .Name = "cmdCancel"
            .Caption = "取消"
            .Left = cmdOK.Left + cmdOK.Width + itemgap
            .Top = cmdOK.Top
            .Width = 60
            .Height = 25
            .Cancel = True ' Allows Esc key to trigger this button
        End With
End Sub

Private Sub chk_TM_Click()
    txt_TM.Enabled = chk_TM.Value
End Sub

Private Sub txt_TM_gotfocus()
    If txt_TM.Text = usrTXT Then
        txt_TM.Text = " "
        txt_TM.ForeColor = &H80
    End If
End Sub

Private Sub txt_TM_Lostfocus()
    If txt_TM.Text = "" Then
        txt_TM.Text = usrTXT
        txt_TM.ForeColor = &H808080
  End If
End Sub

Private Sub cmdOK_Click()
    Dim UpdateTimestamp As Boolean
    Dim ExportToCurrentPath As Boolean
    UpdateTimestamp = chk_TM.Value
    ExportToCurrentPath = chk_Path.Value
    Dim tdy(2)
        tdy(0) = 0
        tdy(2) = 0
        tdy(1) = ""
    If UpdateTimestamp Then
        tdy(0) = 1
        tdy(1) = txt_TM.Text
    End If
    
    If ExportToCurrentPath Then
        tdy(2) = 1
    End If

    dt_pth_ctrl = tdy
'                                        Debug.Print dt_pth_ctrl(0), dt_pth_ctrl(1), dt_pth_ctrl(2)
        Unload Me
End Sub

Private Sub cmdCancel_Click()

    dt_pth_ctrl = Array(0, 0, "")
    Unload Me
End Sub

Attribute VB_Name = "class_PDM"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'我现在希望class PDM类，实现以下多个功能：
' 1  初始化方法， 获取g_rootPrd为catia当前打开的根产品
' 2  catSel1方法  带提示让用户选择单个产品\Part
' 3  catSelx方法 带提示让用户选择多个产品\Part
' 4  infoPrd方法 获取传递的oPrd的一系列属性
' 5  getPara方法  获取 属性或属性值，不存在时返回nothing 和“__”
' 6  meQty 方法  获取产品在当前子总成下的数量
' 7  recurPrd方法  调用infoPrd方法获取根产品及所有子产品的属性，返回为数组，数组第一列为编号，数组第二列为装配层级
' 对于产品发布谁？  质量mass来自usrp
' 对于零件发布谁？ usrp.mass part_info.thickness part_info.density usrp.material
Option Explicit
Public bigbom As Variant
Private osel
Private imsg
Private Att(1 To 10)
Private Const xx = "测试成功"
Private Const xy = "测试失败"
Private Const eklname = "sumVol"
Private Const ekldesc = "sum of vol of bodylist"
Private Const eklstr = "let lst(list) set lst=Part_info\iBodys   let V (Volume) V=0 let i(integer) i=1 for i while i<=lst.Size() {V=V+smartVolume(lst.GetItem(i)) i=i+1} Part_info\sumVol =V"  '使用Const关键字定义常量
Private Sub Class_Initialize()
    iniarr
        On Error GoTo ErrorHandler
        If CATIA.Documents.Count = 0 Then
            Err.Raise 1001, , "未检测到打开的CATIA文档"
            Exit Sub
        End If
            Set rootprd = CATIA.ActiveDocument.Product
        On Error GoTo 0
        
        If Not rootprd Is Nothing Then
            rootprd.ApplyWorkMode (3)
        End If
        Set osel = CATIA.ActiveDocument.Selection: osel.Clear
ErrorHandler:
    If Err.Number <> 0 Then
        Err.Clear
        MsgBox "CATIA 程序错误：" & Err.Description, vbCritical
        Exit Sub
    End If
End Sub
Sub iniarr()
    Att(1) = "Mass"
    Att(2) = "Material"
    Att(3) = "Thickness"
    Att(4) = "Density"
End Sub
' Calculate the total mass of a product and its sub-products
Public Function Assmass(oprd)
        Dim i, total, children
            total = 0
        Set children = oprd.Products
        If oprd.Products.Count > 0 Then
            For i = 1 To children.Count
                Assmass (children.item(i)) 'Assmass = Assmass +
                total = total + children.item(i).ReferenceProduct.UserRefProperties.item("Mass").Value
            Next
            oprd.ReferenceProduct.UserRefProperties.item("Mass").Value = total
        Else
            total = oprd.ReferenceProduct.UserRefProperties.item("Mass").Value
        End If
        Assmass = total
 End Function
' Generate product information
    Public Function infoPrd(oprd)
        Dim Arr(1 To 9)
            With oprd.ReferenceProduct
                Arr(1) = .PartNumber
                Arr(2) = .nomenclature
                Arr(3) = .definition
                Arr(4) = oprd.Name
            End With
        Dim colls
           Set colls = oprd.ReferenceProduct.UserRefProperties
                Arr(5) = getAtt("Material", colls)(1)
                Arr(6) = getAtt("Density", colls)(1)
                Arr(7) = getAtt("Mass", colls)(1)
                Arr(8) = getAtt("Thickness", colls)(1)
        On Error GoTo 0
                Arr(9) = count_me(oprd)
        infoPrd = Arr
    End Function
Public Function recurPrd(oprd, LV)
    Dim mapping As Variant
    mapping = Array(0, 0, 0, 1, 2, 3, 4, 9, 7, 0, 5, 8, 0, 5, 6, 0, 0, 0)
    Dim bomsize
        bomsize = UBound(mapping)
        
    Dim i, j
        If counter = 1 Then
        ReDim bigbom(1 To gfn, 1 To bomsize)
            For i = 1 To gfn
                For j = 1 To bomsize
                    bigbom(i, j) = ""
                Next j
            Next i
    End If   '初始化所有bigbom元素为""
   
    Dim tempdata
    tempdata = infoPrd(oprd)
    
   '=====生成行数据 === bom行数据直接按最大列处理得到一行数据
   
   
        For i = 1 To UBound(bigbom, 2)  '从1到最大列
            bigbom(counter, i) = ""  '默认赋值为空
            Select Case i
                Case 1: bigbom(counter, i) = counter  'counter是全局变量,遍历BOM时为1
                Case 2: bigbom(counter, i) = LV
                Case Else
                    If mapping(i) <= UBound(tempdata) And mapping(i) >= LBound(tempdata) Then '当对应列map值在tempdata元素范围内，
                        bigbom(counter, i) = tempdata(mapping(i))
                    End If
            End Select
           Next
           
            Dim children As Products
            Set children = oprd.Products
            If children.Count > 0 Then
                    Dim bdict
                    Set bdict = CreateObject("Scripting.Dictionary")
                For i = 1 To children.Count
                    If bdict.Exists(children.item(i).PartNumber) = False Then
                       bdict(children.item(i).PartNumber) = 1
                       counter = counter + 1
                       recurPrd children.item(i), LV + 1
                    End If
                Next
            End If
            
  ReDim finalbom(1 To counter, 1 To 17)
  
  For i = 1 To UBound(finalbom, 1)
    For j = 1 To UBound(finalbom, 2)
        finalbom(i, j) = bigbom(i, j)
    Next
  Next
        recurPrd = finalbom
End Function
Public Function modatt(oprd, odata)
    Dim refPrd: Set refPrd = oprd.ReferenceProduct
    Dim colls, i
    Dim currAtt As Variant
     currAtt = infoPrd(oprd)
    For i = 1 To 6
        If odata(i) <> "" Then   'And odata(i) <> currAtt(i)
            On Error Resume Next
                Select Case i
                    Case 1: refPrd.PartNumber = odata(i)
                    Case 2: refPrd.nomenclature = odata(i)
                    Case 3: refPrd.definition = odata(i)
                    Case 4: oprd.Name = odata(i)
                    Case 5:
                        Set colls = refPrd.UserRefProperties
                        colls.item("Material").Value = odata(i)
                    Case 6
                        On Error Resume Next
                            Set colls = refPrd.Parent.part.Parameters.RootParameterSet.ParameterSets.item("Part_info").DirectParameters
                            colls.item("Density").Value = odata(i)
                            Error.Clear
                        On Error GoTo 0
                End Select
                
'                Error.Clear
            On Error GoTo 0
            
        End If
    Next
 End Function
 
Public Sub initPrd(oprd)
    Dim refPrd, colls
    Set refPrd = oprd.ReferenceProduct
    Dim NT As Variant
        NT = Array( _
            Array("Mass", "Mass"), _
            Array("Material", "String"), _
            Array("Thickness", "Length"), _
            Array("Density", "Density") _
        )
    Dim usrp(0 To 0)
    Set colls = refPrd.UserRefProperties
    Dim i
    For i = 0 To 0
        Set usrp(i) = New Class_para
        usrp(i).SetNT NT(i)(0), NT(i)(1)
        checkPara usrp(i), colls
    Next
    On Error Resume Next
         Dim oprt
         Set oprt = refPrd.Parent.part
        If Err.Number <> 0 Then
            Err.Clear
            Set oprt = Nothing
        End If
    On Error GoTo 0
    If Not oprt Is Nothing Then
            Call iniPrt(oprd)
    Else
            Dim k
            k = 0
             Dim oref, pubid, oPub, pubs
           Set pubs = refPrd.Publications
            If getAtt(usrp(k).Name, pubs)(0) Is Nothing Then
                 Dim iName
                 iName = refPrd.PartNumber & "\" & "Properties" & "\" & usrp(k).Name
                Set oref = refPrd.CreateReferenceFromName(iName)
                Debug.Print usrp(k).Name
                Set oPub = pubs.Add(usrp(k).Name)
                pubs.SetDirect usrp(k).Name, oref
            End If
    End If
End Sub

Private Sub iniPrt(oprd)
    Dim refPrd, colls
    Dim i
    Set refPrd = oprd.ReferenceProduct
    Dim oprt: Set oprt = refPrd.Parent.part
'============创建usrp属性=================
    Dim NT As Variant
        NT = Array( _
            Array("Mass", "Mass"), _
            Array("Material", "String"), _
            Array("Thickness", "Length"), _
            Array("Density", "Density") _
        )
    Dim usrp(0 To 3)
    Set colls = refPrd.UserRefProperties
    For i = 0 To 3
        Set usrp(i) = New Class_para
        usrp(i).SetNT NT(i)(0), NT(i)(1)
        checkPara usrp(i), colls
    Next
'============创建part_info内参数=================
    '============创建参数集合=================
        Dim infoset
        Set infoset = New Class_para
        infoset.SetNT "Part_info", "ParameterSet"
        Set colls = oprt.Parameters.RootParameterSet.ParameterSets
        checkPara infoset, colls
        Set colls = infoset.obj.DirectParameters
     '====创建part_info内参数====
        Dim iBodys
        Set iBodys = New Class_para
        iBodys.SetNT "iBodys", "list"
        checkPara iBodys, colls
        If getPara(oprt.mainbody, iBodys.obj.valuelist)(0) Is Nothing Then
                iBodys.obj.valuelist.Add oprt.mainbody
        End If
        Dim infoPara(0 To 3)
        Dim PNT
         PNT = Array( _
            Array("sumVol", "Volume"), _
            Array("Thickness", "Length"), _
            Array("Density", "Density"), _
            Array("Mass", "Mass") _
        )
        For i = 0 To 3
            Set infoPara(i) = New Class_para
            infoPara(i).SetNT PNT(i)(0), PNT(i)(1)
            checkPara infoPara(i), colls
        Next
    '======创建零件发布======
        Dim oref, pubid, oPub, pubs
        Set pubs = refPrd.Publications
         Dim k
          For k = 1 To 3
               If getAtt(infoPara(k).Name, pubs)(0) Is Nothing Then
                   Dim iName
                   iName = refPrd.PartNumber & "\Parameters\Part_info\" & infoPara(k).Name
                   Set oref = refPrd.CreateReferenceFromName(iName)
                   Set oPub = pubs.Add(infoPara(k).Name)
                   pubs.SetDirect infoPara(k).Name, oref
               Else
               Debug.Print "不需要发布" & infoPara(k).Name
                End If
           Next
    '创建所有relations
            Set colls = oprt.relations
            Dim oRule
            Set oRule = New Class_para
                   '---创建EKL
            oRule.Reset
            oRule.SetNT "sum_all_Vol", "Program"
            oRule.Str = eklstr
            oRule.Desc = "汇总体积"
            checkPara oRule, colls
                    '---创建Cal_mass
            oRule.Reset
            oRule.SetNT "cal_Mass", "Formula"
            oRule.Desc = "链接重量"
    
            oRule.Str = "round(Part_info\sumVol *Part_info\Density,""kg"",3)"   ''''"Part_info\sumVol *Part_info\Density"
            Set oRule.Target = infoPara(3).obj
            checkPara oRule, colls
                    '---创建link_mass
            oRule.Reset
            oRule.SetNT "link_Mass", "Formula"
            oRule.Desc = "链接重量"
            oRule.Str = "Part_info\Mass"
            Set oRule.Target = refPrd.UserRefProperties.item("Mass")
            checkPara oRule, colls
                    '---创建link_thickness
            oRule.Reset
            oRule.SetNT "link_Thickness", "Formula"
            oRule.Desc = "链接厚度"
            oRule.Str = "Part_info\Thickness"
            Set oRule.Target = refPrd.UserRefProperties.item("Thickness")
            checkPara oRule, colls
                    '---创建link_Density
            oRule.Reset
            oRule.SetNT "link_Density", "Formula"
            oRule.Desc = "链接密度"
            oRule.Str = "Part_info\Density"
            Set oRule.Target = refPrd.UserRefProperties.item("Density")
            checkPara oRule, colls
            oRule.Reset
End Sub
Private Function checkPara(thispara, colls)
    If getPara(thispara, colls)(0) Is Nothing Then
'        Debug.Print "需要创建" & thispara.Name
        paraCreatobj thispara, colls   '创建参数和公式时已经是默认值'
    Else
'        Debug.Print "不需要创建" & thispara.obj.Name
        Set thispara.obj = getPara(thispara, colls)(0) '已有参数和公式，校验默认值'
        Select Case thispara.iType  '只有formula和rule才需要校核其内容
            Case "Program", "Formula"
                If thispara.obj.Value <> thispara.Str Then
                 thispara.obj.Modify thispara.Str
'                  Debug.Print "已经修改" & thispara.obj.Name
                End If
                thispara.obj.Hidden = True
        End Select
    End If
End Function
Private Function getPara(thispara, collection)
    Dim Arr(1) ' 正确声明数组
    On Error Resume Next
        Set Arr(0) = collection.item(thispara.Name)
        If Err.Number = 0 Then ' 检查是否成功获取对象
            Arr(1) = Arr(0).Value
            getPara = Arr
        Else
            getPara = Array(Nothing, "__")
        End If
    On Error GoTo 0
End Function
Private Function getAtt(iName, collection)
    Dim Arr(1) ' 正确声明数组
    On Error Resume Next
        Set Arr(0) = collection.item(iName)
        If Err.Number = 0 Then ' 检查是否成功获取对象
            Arr(1) = Arr(0).Value
            getAtt = Arr
        Else
            getAtt = Array(Nothing, "__")
        End If
    On Error GoTo 0
End Function
Private Function paraCreatobj(thispara, colls)
        Select Case thispara.iType
            Case "ParameterSet"
                Set thispara.obj = colls.CreateSet(thispara.Name)
            Case "list"
                Set thispara.obj = colls.CreateList(thispara.Name)
            Case "Mass", "Density", "Length", "Volume" '所有dimension参数
                Set thispara.obj = colls.CreateDimension(thispara.Name, thispara.iType, thispara.Str)
            Case "String"
                Set thispara.obj = colls.CreateString(thispara.Name, thispara.Str)
            Case "Formula"
                Set thispara.obj = colls.CreateFormula(thispara.Name, thispara.Desc, thispara.Target, thispara.Str)
                 thispara.obj.Hidden = True
            Case "Program"
                  On Error Resume Next
                    Set thispara.obj = colls.CreateProgram(thispara.Name, thispara.Desc, thispara.Str)
                  If Error.Number <> 0 Then
                    Debug.Print "缺少KWA lisence, 无法创建rule单位"
                  End If
                    Error.Clear
                  On Error GoTo 0
    End Select
    Debug.Print "已经创建" & thispara.Name
End Function
Private Function count_me(oprd)  '获取兄弟字典
     Dim i, oDict, QTy, pn
         QTy = 1
     On Error Resume Next
          If TypeOf oprd.Parent Is Products Then    '若有父级产品'获取兄弟字典
                    Dim oParent: Set oParent = oprd.Parent.Parent
                   Set oDict = CreateObject("Scripting.Dictionary")
                   For i = 1 To oParent.Products.Count
                          pn = oParent.Products.item(i).PartNumber
                            If oDict.Exists(pn) = True Then
                                oDict(pn) = oDict(pn) + 1
                            Else
                                oDict(pn) = 1
                            End If
                      Next
            QTy = oDict(oprd.PartNumber)
          End If
    count_me = QTy
End Function
Public Function catSel1(prompt As String) As Object
    osel.Clear
    Dim iType(0)
    iType(0) = "Product"
        MsgBox prompt
    If osel.SelectElement2(iType, prompt, False) = "Normal" Then
        If osel.Count = 1 Then
            Set catSel1 = osel.item(1).LeafProduct
        End If
    End If
    osel.Clear
End Function
Public Function catSelx(prompt As String) As collection
    Set catSelx = New collection
    osel.Clear
    Dim iType(0)
    iType(0) = "Product"
    If osel.SelectElement3(iType, prompt, True, 2, True) = "Normal" Then
        Dim i As Integer
        For i = 1 To osel.Count
            catSelx.Add osel.item(i).LeafProduct
        Next
    End If
    osel.Clear
End Function
Public Function defgprd()    '获取要读取或修改的  全局变量 gPrd定义
     imsg = MsgBox("“是”选择产品，“否”读取根产品，“取消退出”", vbYesNoCancel + vbDefaultButton2, "请选择产品")
     Dim oprd
     
     Set oprd = Nothing
     
        Select Case imsg
            Case 7 '===选择“否”====
            Set rootprd = CATIA.ActiveDocument.Product
            Set oprd = rootprd
            Case 2:
            
            
           Set oprd = Nothing
            Case 6  '===选择“是”,进行产品选择====
                On Error Resume Next
                    Set oprd = selPrd()
                If Err.Number <> 0 Then
                    Err.Clear
                    Exit Function
                End If
        End Select
        
        Set defgprd = oprd
        Set oprd = Nothing
End Function
Public Sub freePrd()
     Set gPrd = Nothing

End Sub
Public Function selPrd()
    osel.Clear
   Dim status, iType(0)
'   catia.ActiveWindow.WindowState = 0
    osel.Clear
    iType(0) = "Product"
    If osel.Count2 = 0 Then
         ' MsgBox "请在CATIA结构树选择要读取的产品"
        status = osel.SelectElement2(iType, "请选择要读取的产品", False)
        'status = oSel.SelectElement3(iType, "请选择要读取的产品", True, 2, False)
    End If
    If status = "Cancel" Then
        Exit Function
    End If
    If status = "Normal" And osel.Count2 = 1 Then
            Set selPrd = osel.item(1).LeafProduct.ReferenceProduct
          '  MsgBox "你选择的产品是" & selPrd.PartNumber
            osel.Clear
    Else
        MsgBox "请只选择一个产品"
        Exit Function
    End If
End Function
Public Function gxBom(oprd, LV)
    Dim mapping As Variant
    mapping = Array(0, 0, 0, 0, 0, 0, 1, 0, 3, 2, 0, 9, 0, 7, 0, 5, 0)
    Dim bomsize
        bomsize = UBound(mapping)
    Dim i, j
        If counter = 1 Then
        ReDim bigbom(1 To gfn, 1 To bomsize)
            For i = 1 To gfn
                For j = 1 To bomsize
                    bigbom(i, j) = ""
                Next j
            Next i
    End If   '初始化所有bigbom元素为""
    Dim tempdata
    tempdata = infoPrd(oprd)
   '=====生成行数据 === bom行数据直接按最大列处理得到一行数据
        For i = 1 To UBound(bigbom, 2)  '从1到最大列
            bigbom(counter, i) = ""  '默认赋值为空
            Select Case i
                Case 1: bigbom(counter, i) = counter  'counter是全局变量,遍历BOM时为1
                Case 2, 3, 4, 5:
                    If LV <= 4 Then
                        If LV = i - 1 Then
                            bigbom(counter, i) = LV
                        End If
                     Else
                     bigbom(counter, i) = "error"
                    End If
            
                Case Else
                    If mapping(i) <= UBound(tempdata) And mapping(i) >= LBound(tempdata) Then '当对应列map值在tempdata元素范围内，
                        bigbom(counter, i) = tempdata(mapping(i))
                    End If
            End Select
           Next
            Dim children As Products
            Set children = oprd.Products
            If children.Count > 0 Then
                    Dim bdict
                    Set bdict = CreateObject("Scripting.Dictionary")
                For i = 1 To children.Count
                    If bdict.Exists(children.item(i).PartNumber) = False Then
                       bdict(children.item(i).PartNumber) = 1
                       counter = counter + 1
                       gxBom children.item(i), LV + 1
                    End If
                Next
            End If
  ReDim finalbom(1 To counter, 1 To 16)
  For i = 1 To UBound(finalbom, 1)
    For j = 1 To UBound(finalbom, 2)
        finalbom(i, j) = bigbom(i, j)
    Next
  Next
        gxBom = finalbom
End Function

Attribute VB_Name = "clsCtrls"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public WithEvents txt As MSForms.TextBox
Attribute txt.VB_VarHelpID = -1
Public ohint As String


Private Sub txt_Gotfocus()

If txt.Text = ohint Then txt.Text = "": txt.ForeColor = &H0

End Sub
Private Sub txt_Lostfocus()

If txt.Text = "" Then txt.Text = ohint: txt.ForeColor = &H808080

End Sub

Attribute VB_Name = "global_var"

Public gPrd As Object
Public rootprd  As Object  '全局产品obj
Public startrow, lastRow  '全局excel行定义
Public xlAPP As Object  '全局excelcom组件
Public gwb As Object
Public gws  As Object
Public pdm As Object
Public xlm As Object
Public allPN As Object
Public counter As Integer
Public Const gfn As Integer = 400
Public ProductObserver As New ProductObserver
Public dt_pth_ctrl





Sub clearall()



End Sub

Attribute VB_Name = "m0_dataMenu"
'Attribute VB_Name = "Cat_Macro_Menu_Model"
' 此代码用于获取宏菜单所需的配置信息并展示菜单界面
Const FormTitle = "Macro"
'----- 菜单的配置信息 ---------------------------------------
' 菜单的显示类型
' True - 非模态显示  False - 模态显示
Private Const MENU_SHOW_TYPE = True
' 菜单的隐藏类型
' True - 隐藏菜单按钮  False - 显示菜单按钮
Private Const MENU_HIDE_TYPE = True
' 菜单分组的配置信息
' 请根据需要修改
'{ 分组编号 : 分组标题 }
' 示例配置
Private Const groupName = _
            "{1 : DRW }" & _
            "{2 : MDL }" & _
            "{3 : ASM }" & _
            "{4 : R&W }" & _
            "{5 : BOM  }" & _
            "{6 : OTRS }"
'-----------------------------------------------------------------
Option Explicit
'----- 配置参数 请勿修改除非必要 -----------------------
' 菜单分组映射表
Private PageMap As Object
' 标签映射表
Private TagMap As Object                    ' 分组编号标签
Private Const TAG_S = "{"                   ' 配置开始标签
Private Const TAG_D = ":"                   ' 配置分隔标签
Private Const TAG_E = "}"                   ' 配置结束标签
Private Const TAG_GROUP = "gp"              ' 分组编号标签
Private Const TAG_ENTRYPNT = "ep"           ' 入口点标签
Private Const TAG_ENTRY_DEF = "CATMain"     ' 入口点默认值
Private Const TAG_PJTPATH = "pjt_path"      ' 项目路径标签
Private Const TAG_MDLNAME = "mdl_name"      ' 模块名称标签
'-----------------------------------------------------------------
' 菜单入口点
Sub CATMain()
    Set PageMap = Get_KeyValue(groupName, True)
    Dim ButtonInfos As Object
    Set ButtonInfos = Get_ButtonInfo()
    If ButtonInfos Is Nothing Then
        MsgBox "未找到可用的宏信息", vbExclamation + vbOKOnly
        Exit Sub
    End If
    ' 对按钮信息进行排序
    Dim SoLst As Object
    Set SoLst = To_SortedList(ButtonInfos)
    If SoLst Is Nothing Then Exit Sub
    ' 显示菜单界面
    Dim Menu
    Set Menu = New Cat_Macro_Menu_View
    Call Menu.Set_FormInfo(SoLst, PageMap, FormTitle, MENU_HIDE_TYPE)
    
    If MENU_SHOW_TYPE Then
        Menu.Show vbModeless
    Else
        Menu.Show vbModal
    End If
End Sub
'******* 辅助函数 *********
' 获取宏按钮的配置信息
' 参数  :
' 返回值: lst(Dict)
Private Function Get_ButtonInfo() As Object
    Set Get_ButtonInfo = Nothing
    
    Dim Apc As Object: Set Apc = GetApc()
    Dim ExecPjt As Object: Set ExecPjt = Apc.ExecutingProject
    Dim PjtPath As String: PjtPath = ExecPjt.DisplayName
    
    Dim AllComps As Object
    Set AllComps = GetModuleLst(ExecPjt.ProjectItems.VBComponents)
    If AllComps Is Nothing Then Exit Function
    
    Dim Comp As Object 'VBComponent
    Dim Mdl As Object 'CodeModule
    Dim DecCode As String
    Dim DecCnt As Long
    Dim MdlInfo As Object
    Dim CanExecMethod As String
    Dim BtnInfos As Object: Set BtnInfos = KCL.InitLst()
    
    For Each Comp In AllComps
        Set Mdl = Comp.CodeModule
        ' 获取声明行数
        DecCnt = Mdl.CountOfDeclarationLines
        If DecCnt < 1 Then GoTo continue
        ' 获取声明代码
        DecCode = Mdl.Lines(1, Mdl.CountOfDeclarationLines)
        ' 获取配置信息
        Set MdlInfo = Get_KeyValue(DecCode)
        If MdlInfo Is Nothing Then GoTo continue
        ' 检查分组信息
        If Not MdlInfo.Exists(TAG_GROUP) Then GoTo continue
        If IsNumeric(MdlInfo(TAG_GROUP)) Then
            MdlInfo(TAG_GROUP) = CLng(MdlInfo(TAG_GROUP))
        Else
            GoTo continue
        End If
        Debug.Print TypeName(MdlInfo(TAG_GROUP)) & " : " & MdlInfo(TAG_GROUP)
        If Not PageMap.Exists(MdlInfo(TAG_GROUP)) Then GoTo continue
        
        ' 检查入口点方法
        CanExecMethod = vbNullString
        If MdlInfo.Exists(TAG_ENTRYPNT) Then
            If Exist_Method(Mdl, MdlInfo(TAG_ENTRYPNT)) Then
                CanExecMethod = MdlInfo(TAG_ENTRYPNT)
            Else
                GoTo Try_TAG_ENTRY_DEF
            End If
        Else
Try_TAG_ENTRY_DEF:
            If Exist_Method(Mdl, TAG_ENTRY_DEF) Then
                 CanExecMethod = TAG_ENTRY_DEF
            End If
        End If
        If CanExecMethod = vbNullString Then GoTo continue
        Set MdlInfo = Push_Dic(MdlInfo, TAG_ENTRYPNT, CanExecMethod)
        Set MdlInfo = Push_Dic(MdlInfo, TAG_PJTPATH, PjtPath)
        Set MdlInfo = Push_Dic(MdlInfo, TAG_MDLNAME, Mdl.Name)
        BtnInfos.Add MdlInfo
continue:
    Next
    If BtnInfos.Count < 1 Then Exit Function
    Set Get_ButtonInfo = BtnInfos
End Function
' 向字典中添加或更新键值对
' 参数  : Dict,vri,vri
' 返回值: Dict
Private Function Push_Dic(ByVal Dic As Object, _
                          ByVal Key As Variant, _
                          ByVal item As Variant) As Object
    If Dic.Exists(Key) Then
        Dic(Key) = item
    Else
        Dic.Add Key, item
    End If
    Set Push_Dic = Dic
End Function
' 从字符串中提取配置信息 - 键转换为长整型
' 参数  : str,Opt_bool
' 返回值: Dict
Private Function Get_KeyValue( _
                    ByVal txt As String, _
                    Optional ByVal KeyToLong As Boolean = False) _
                    As Object
    Set Get_KeyValue = Nothing
    Dim Reg As Object
    Set Reg = CreateObject("VBScript.RegExp")
    With Reg
        .Pattern = TAG_S & "(.*?)" & TAG_D & "(.*?)" & TAG_E
        .Global = True
    End With
    
    Dim Matches As Object
    Set Matches = Reg.Execute(txt)
    Set Reg = Nothing
    
    If Matches.Count < 1 Then Exit Function
    
    Dim Dic As Object: Set Dic = KCL.InitDic(vbTextCompare)
    Dim Match As Object, SubMatchs As Object
    Dim Key As Variant, Var As Variant
    
    For Each Match In Matches
        Set SubMatchs = Match.SubMatches
        
        If SubMatchs.Count < 2 Then GoTo continue
        
        Key = Trim(Replace(SubMatchs(0), """", ""))
        If Len(Key) < 1 Then GoTo continue
        If KeyToLong Then Key = CLng(Key)
        
        Var = Trim(Replace(SubMatchs(1), """", ""))
        If Len(Var) < 1 Then GoTo continue
        
        Set Dic = Push_Dic(Dic, Key, Var)
continue:
    Next
    
    If Dic.Count < 1 Then Exit Function
    
    Set Get_KeyValue = Dic
End Function
' 将按钮信息按分组排序
' 参数  :lst(Dict)
' 返回值: Dict(lst(Dict))
Private Function To_SortedList(ByVal Infos As Object) As Object
    Set To_SortedList = Nothing
    
    Dim SoLst As Object
    Set SoLst = CreateObject("System.Collections.SortedList")
    Dim lst As Object
    
    Dim Info As Object
    For Each Info In Infos
        If SoLst.ContainsKey(Info(TAG_GROUP)) = True Then
            SoLst(Info(TAG_GROUP)).Add Info
        Else
            Set lst = KCL.InitLst()
            lst.Add Info
            SoLst.Add Info(TAG_GROUP), lst
        End If
    Next
    
    If SoLst.Count < 1 Then Exit Function
    
    ' 按模块名称排序
    Dim i As Long
    Dim InfoDic As Object: Set InfoDic = KCL.InitDic(vbTextCompare)
    For i = 0 To SoLst.Count - 1
        InfoDic.Add SoLst.GetKey(i), Sort_by(SoLst.GetByIndex(i))
    Next
    
    Set To_SortedList = InfoDic
End Function
' 按模块名称排序
' 参数  :lst(Dict)
' 返回值: lst(Dict)
Private Function Sort_by(ByVal lst As Object) As Object
    Dim tmp As Object
    Dim i As Long, j As Long
    Set tmp = lst(0)
    For i = 0 To lst.Count - 1
        For j = lst.Count - 1 To i Step -1
            If lst(i)(TAG_MDLNAME) > lst(j)(TAG_MDLNAME) Then
                Set tmp = lst(i)
                Set lst(i) = lst(j)
                Set lst(j) = tmp
            End If
        Next j
    Next i
    Set Sort_by = lst
End Function
'******* APC/VBE *********
' 获取APC对象
' 参数  :
' 返回值: obj-IApc
Private Function GetApc() As Object
    Set GetApc = Nothing
    
    ' 获取VBA版本对应的COM对象名称
    Dim COMObjectName$
    #If VBA7 Then
        COMObjectName = "MSAPC.Apc.7.1"
    #ElseIf VBA6 Then
        COMObjectName = "MSAPC.Apc.6.2"
    #Else
        MsgBox "不支持当前VBA版本", vbExclamation + vbOKOnly
        Exit Function
    #End If
    
    ' 获取APC对象
    Dim Apc As Object: Set Apc = Nothing
    On Error Resume Next
        Set Apc = CreateObject(COMObjectName)
    On Error GoTo 0
    
    If Apc Is Nothing Then
        MsgBox "无法获取MSAPC.Apc对象", vbExclamation + vbOKOnly
        Exit Function
    End If
    
    Set GetApc = Apc
End Function
' 检查代码模块中是否存在指定方法 - 不检查私有方法
' 参数  : obj-CodeModule,str
' 返回值: Boolean
Private Function Exist_Method(ByVal CodeMdl As Object, _
                              ByVal Name As String) As Boolean
    Dim tmp As Long
    On Error Resume Next
        tmp = CodeMdl.ProcBodyLine(Name, 0)
    On Error GoTo 0
    Exist_Method = tmp > 0
    Err.Number = 0
End Function
' 获取标准模块列表
' 参数  : obj-VBComponents
' 返回值: lst(obj-VBComponent)
' vbext_ComponentType
' 1-vbext_ct_StdModule 2-vbext_ct_ClassModule 3-vbext_ct_MSForm
Private Function GetModuleLst(ByVal Itms As Object) As Object
    Set GetModuleLst = Nothing
    Dim lst As Object: Set lst = KCL.InitLst()
    Dim Itm As Object
    For Each Itm In Itms
        If Not Itm.Type = 1 Then GoTo continue 'vbext_ComponentType
        lst.Add Itm
continue:
    Next
    If lst.Count < 1 Then Exit Function
    Set GetModuleLst = lst
End Function

Attribute VB_Name = "m10_closePartWindows"
'Attribute VB_Name = "m10_closePartWindows"
' Part窗口一次性全关闭
'{GP:1}
'{EP:CLSpart}
'{Caption:关闭零件窗口}
'{ControlTipText: 点击后一次性全关闭所有零件窗口}
'{背景颜色: 12648447}

Sub CLSpart()
Dim CATIA, wds, wd
 On Error Resume Next
    Set CATIA = GetObject(, "CATIA.Application")
    Set wds = CATIA.Windows
    If wds.Count < 1 Then
           MsgBox "没有打开的窗口"
           Exit Sub
    End If
    For i = 1 To wds.Count
        Set wd = wds.item(i)
        If KCL.IsType_Of_T(wd.Parent, "PartDocument") Then
            wd.Close
        End If
    Next
    On Error GoTo 0
End Sub

'

Attribute VB_Name = "m11_DrwLock"
'Attribute VB_Name = "sample_Draft_View_Lock_UnLock"
' 图纸视图的锁定与解锁
'{GP:1}
'{EP:CATMain}
'{Caption:锁定_解锁}
'{ControlTipText: 可以进行图纸视图的锁定与解锁}
'{背景颜色: 12648447}

Option Explicit
Sub CATMain()
' 检查是否可以执行
     If Not CanExecute("DrawingDocument") Then
          Exit Sub
     End If
     
     Dim Views As DrawingViews
     Set Views = CATIA.ActiveDocument.Sheets.ActiveSheet.Views
     If Views.Count < 3 Then
                 Exit Sub
      End If
            
            Dim View As DrawingView
                 Set View = Views.item(3)
                 
            Dim LockState As Boolean
                 LockState = View.LockStatus
            
            Dim msg As String
            
            If LockState Then
                 msg = "解锁"
               LockState = False
            Else
                 msg = "锁定"
               LockState = True
            End If
     If Views.Count > 3 Then
            Dim i As Long
            For i = 3 To Views.Count
                 Set View = Views.item(i)
                      View.LockStatus = LockState
                 Next
     End If
     MsgBox "视图已成功" & msg & "。"
End Sub

Attribute VB_Name = "m12_Tb2xl"
'Attribute VB_Name = "m12_Tb2xl"
' 图纸视图的锁定与解锁
'{GP:1}
'{EP:Tb2xl}
'{Caption:2D表格导出}
'{ControlTipText: 提示选择2图纸中表格后导出}
'{BackColor:12648447}




Sub Tb2xl()

  If Not CanExecute("DrawingDocument") Then
          Exit Sub
     End If

    Dim oDoc As DrawingDocument
    Set oDoc = CATIA.ActiveDocument
    

    Dim oSHT As DrawingSheet
    Set oSHT = oDoc.Sheets.ActiveSheet
    
    ' set drawing drwView
    Dim oView As DrawingView
    Set oView = oSHT.Views.ActiveView
    

    Dim imsg
    imsg = "请选择table"
    
    Dim drwTable
    Set drwTable = KCL.SelectItem(imsg, DrawingTable)
  
    If Not drwTable Is Nothing Then
        Dim rowsNo As Long
        rowsNo = drwTable.NumberOfRows
    
        Dim colsNo As Long
        colsNo = drwTable.NumberOfColumns
        
        
        Dim i As Long, j As Long
        ReDim Arr(rowsNo - 1, colsNo - 1) As Variant
      
        For i = 1 To rowsNo
            For j = 1 To colsNo
                ' write cell content to an array item
                Arr(i - 1, j - 1) = drwTable.GetCellString(i, j)
            Next
        Next
        
        ArrayToxl Arr
    Else
    
    MsgBox "无可操作表格，请检查"
    Exit Sub
    End If


End Sub


Sub ArrayToxl(arr2D() As Variant)
    Dim xlAPP As Object
    Set xlAPP = CreateObject("Excel.Application")
    Dim wbook As Object
    Set wbook = xlAPP.Workbooks.Add
    Dim rng As Object
    Set rng = wbook.Sheets(1).Range("B2")
    
    With rng.Resize(UBound(arr2D, 1) + 1, UBound(arr2D, 2) + 1)
        .Value = arr2D
        .Borders.LineStyle = xlContinuous
        .Borders.Weight = xlThin
        .Borders.ColorIndex = 0
    End With
    
    xlAPP.Visible = True
End Sub

Attribute VB_Name = "m1_cRelation"

Sub CATMain()

Dim partDocument1 As PartDocument
Set partDocument1 = CATIA.ActiveDocument

Dim selection1 As Selection
Set selection1 = partDocument1.Selection

selection1.Clear

Dim knowledgeObject1 As KnowledgeObject
' No resolution found for the object knowledgeObject1...

Dim anyObject1 As AnyObject
Set anyObject1 = knowledgeObject1.GetItem(">Part Info")

selection1.Add anyObject1

selection1.Copy

End Sub

Attribute VB_Name = "m20_newgeo"
'Attribute VB_Name = "m20_newgeo"
'{GP:2}
'{Ep:newgeo}
'{Caption:创建几何树}
'{ControlTipText:创建基于模板的几何树}
'{BackColor: }

Private oprt

Sub newgeo()
 If Not CanExecute("PartDocument") Then Exit Sub
 
Set oDoc = CATIA.ActiveDocument.Product
Set oprt = oDoc.ReferenceProduct.Parent.part
Set colls = oprt.HybridBodies
On Error Resume Next
Set og = colls.item("Geo_sheet")
On Error GoTo 0


Set og = colls.Add()
crSkt og
og.Name = "GEO_sheet"
Set colls = og.HybridBodies
Arr = Array("01_Profile", "02_Ribs", "03_Assy", "04_trim", "05_Pierce", "06_final part")
For i = 0 To UBound(Arr)
    Set og = colls.Add()
    og.Name = Arr(i)
    Next
End Sub
Sub crSkt(og)
oprt.InWorkObject = og
Set HSF = oprt.HybridShapeFactory
Set oPoint = HSF.AddNewPointCoord(0#, 0#, 0#)
og.AppendHybridShape oPoint
oprt.InWorkObject = oPoint
oprt.Update
Set oPln = HSF.AddNewPlaneEquation(0#, 0#, 1#, 20#)
Set pref = oPoint
Set oref = oprt.CreateReferenceFromObject(pref)
oPln.SetReferencePoint oPoint  'oref
og.AppendHybridShape oPln
oprt.InWorkObject = oPln
oprt.Update
Set SKTs = og.HybridSketches
Set oSkt = og.HybridSketches.Add(oPln)
oprt.InWorkObject = oSkt
Set factory2D1 = oSkt.OpenEdition()
Set geometricElements1 = oSkt.geometricElements
Set axis2D1 = geometricElements1.item("AbsoluteAxis")
Set line2D1 = axis2D1.GetItem("HDirection")
line2D1.ReportName = 1
Set line2D2 = axis2D1.GetItem("VDirection")
line2D2.ReportName = 2
Set circle2D1 = factory2D1.CreateClosedCircle(0#, 0#, 10#)
Set point2D1 = axis2D1.GetItem("Origin")
circle2D1.CenterPoint = point2D1
circle2D1.ReportName = 3
oSkt.CloseEdition
oprt.InWorkObject = og
oprt.Update
''the first 3 being the coordinates of the axis origin,
'Dim arr(0 To 8)
'arr(0) = 0
'arr(1) = 0#
'arr(2) = 0#
'the next 3 being those of the horizontal axis,
'arr(3) = 1#
'arr(4) = 0#
'arr(5) = 0#
'
''and the last 3 those of the vertical axis of the absolute axis.
'arr(6) = 0#
'arr(7) = 1#
'arr(8) = 0#
'oSkt.SetAbsoluteAxisData (arr)
End Sub

Attribute VB_Name = "m21_Part2Product"
'Attribute VB_Name = "m2_Part2Product"
'{控件提示文本: 可将零件转换为产品}
' 检查零件文档中是否存在左手坐标系
'{Gp:2}
'{Ep:CATMain}
'{Caption:零件转产品}
'{ControlTipText:此按钮将多实体零件转化为产品}
'{BackColor:}
Option Explicit

Sub CATMain()
    If Not CanExecute("PartDocument") Then Exit Sub
    Dim BaseDoc As PartDocument: Set BaseDoc = CATIA.ActiveDocument
    Dim BasePath As Variant: BasePath = Array(BaseDoc.FullName)
    Dim Pt As part: Set Pt = BaseDoc.part
    Dim LeafItems As collection: Set LeafItems = Get_LeafItemLst(Pt.Bodies)
    Dim msg As String
    If LeafItems Is Nothing Then
        msg = "没有可复制的元素！"
        MsgBox msg, vbOKOnly + vbExclamation
        Exit Sub
    End If
    msg = LeafItems.Count & " 个可复制的元素。" & vbNewLine & _
          "请指定粘贴的类型" & vbNewLine & vbNewLine & _
          "是 : 带链接的结果(As Result With Link)" & vbNewLine & _
          "否 : 作为结果(As Result)" & vbNewLine & _
          "取消 : 宏中止"
    Dim PasteType As String
    Select Case MsgBox(msg, vbQuestion + vbYesNoCancel)
        Case vbYes
            PasteType = "CATPrtResult"
        Case vbNo
            PasteType = "CATPrtResultWithOutLink"
        Case Else
            Exit Sub
    End Select
    KCL.SW_Start
    Dim BaseScene As Variant: BaseScene = GetScene3D(GetViewPnt3D())
    Dim TopDoc As productDocument: Set TopDoc = CATIA.Documents.Add("Product")
    Call ToProduct(TopDoc, LeafItems, PasteType)
    Call UpdateScene(BaseScene)
    TopDoc.Product.Update
    Debug.Print "时间:" & KCL.SW_GetTime & "s"
    MsgBox "完成"
End Sub

Private Sub ToProduct(ByVal TopDoc As productDocument, _
                      ByVal LeafItems As collection, _
                      ByVal PasteType As String)
    Dim TopSel As Selection
    Set TopSel = TopDoc.Selection
    Dim BaseSel As Selection
    Set BaseSel = KCL.GetParent_Of_T(LeafItems(1), "PartDocument").Selection
    Dim Prods As Products
    Set Prods = TopDoc.Product.Products
    Dim Itm As AnyObject
    Dim TgtDoc As PartDocument
    Dim ProdsNameDic As Object: Set ProdsNameDic = KCL.InitDic()
    CATIA.HSOSynchronized = False
    For Each Itm In LeafItems
        If ProdsNameDic.Exists(Itm.Name) Then
            Set TgtDoc = ProdsNameDic.item(Itm.Name)
        Else
            Set TgtDoc = Init_Part(Prods, Itm.Name)
            ProdsNameDic.Add Itm.Name, TgtDoc
        End If
        Call Preparing_Copy(BaseSel, Itm)
        With BaseSel
            .Copy
            .Clear
        End With
        With TopSel
            .Clear
            .Add TgtDoc.part
            .PasteSpecial PasteType
        End With
    Next
    BaseSel.Clear
    TopSel.Clear
    CATIA.HSOSynchronized = True
End Sub

Private Sub Preparing_Copy(ByVal sel As Selection, ByVal Itm As AnyObject)
    sel.Clear
    If TypeName(Itm) = "Body" Then
        sel.Add Itm
        Exit Sub
    End If
    Dim ShpsLst As collection: Set ShpsLst = New collection
    ShpsLst.Add Itm.HybridShapes
    Select Case TypeName(Itm)
        Case "HybridBody"
            Set ShpsLst = Get_All_HbShapes(Itm, ShpsLst)
        Case "OrderedGeometricalSet"
            Set ShpsLst = Get_All_OdrGeoSetShapes(Itm, ShpsLst)
    End Select
    Dim Shps As HybridShapes, Shp As HybridShape
    For Each Shps In ShpsLst
        For Each Shp In Shps
            sel.Add Shp
        Next
    Next
End Sub

Private Function Get_All_OdrGeoSetShapes(ByVal OdrGeoSet As OrderedGeometricalSet, _
                                         ByVal lst As collection) As collection
    Dim child As OrderedGeometricalSet
    For Each child In OdrGeoSet.OrderedGeometricalSets
        lst.Add child.HybridShapes
        If child.OrderedGeometricalSets.Count > 0 Then
            Set lst = Get_All_OdrGeoSetShapes(child, lst)
        End If
    Next
    Set Get_All_OdrGeoSetShapes = lst
End Function

Private Function Get_All_HbShapes(ByVal Hbdy As HybridBody, _
                                  ByVal lst As collection) As collection
    Dim child As HybridBody
    For Each child In Hbdy.HybridBodies
        lst.Add child.HybridShapes
        If child.HybridBodies.Count > 0 Then
            Set lst = Get_All_HbShapes(child, lst)
        End If
    Next
    Set Get_All_HbShapes = lst
End Function

Private Function Get_LeafItemLst(ByVal Pt As part) As collection
    Set Get_LeafItemLst = Nothing
    Dim sel As Selection: Set sel = Pt.Parent.Selection
    Dim TmpLst As collection: Set TmpLst = New collection
    Dim i As Long
    Dim filter As String
    filter = "(CATPrtSearch.BodyFeature.Visibility=Shown " & _
            "+ CATPrtSearch.OpenBodyFeature.Visibility=Shown" & _
            "+ CATPrtSearch.MMOrderedGeometricalSet.Visibility=Shown),sel"
    CATIA.HSOSynchronized = False
    With sel
        .Clear
        .Add Pt
        .Search filter
        For i = 1 To .Count2
            TmpLst.Add .item(i).Value
        Next
        .Clear
    End With
    CATIA.HSOSynchronized = True
    If TmpLst.Count < 1 Then Exit Function
    Dim LeafHBdys As Object: Set LeafHBdys = KCL.InitDic()
    Dim Hbdy As AnyObject
    For Each Hbdy In Pt.HybridBodies
        LeafHBdys.Add Hbdy, 0
    Next
    For Each Hbdy In Pt.OrderedGeometricalSets
        LeafHBdys.Add Hbdy, 0
    Next
    Dim Itm As AnyObject
    Dim lst As collection: Set lst = New collection
    For Each Itm In TmpLst
        Select Case TypeName(Itm)
            Case "Body"
                If Is_LeafBody(Itm) Then lst.Add Itm
            Case Else
                If Is_LeafHybridBody(Itm, LeafHBdys) Then lst.Add Itm
        End Select
    Next
    If lst.Count < 1 Then Exit Function
    Set Get_LeafItemLst = lst
End Function

Private Function Is_LeafBody(ByVal Bdy As Body) As Boolean
    Is_LeafBody = Bdy.InBooleanOperation = False And Bdy.Shapes.Count > 0
End Function

Private Function Is_LeafHybridBody(ByVal Hbdy As AnyObject, _
                                   ByVal Dic As Object) As Boolean
    Is_LeafHybridBody = False
    If Not Dic.Exists(Hbdy) Then Exit Function
    CATIA.HSOSynchronized = False
    Dim sel As Selection
    Set sel = KCL.GetParent_Of_T(Hbdy, "PartDocument").Selection
    Dim Cnt As Long
    With sel
        .Clear
        .Add Hbdy
        .Search "Visibility=Shown,sel"
        Cnt = .Count2
        .Clear
    End With
    CATIA.HSOSynchronized = True
    If Cnt > 1 Then Is_LeafHybridBody = True
End Function

Private Function Init_Part(ByVal Prods As Variant, _
                           ByVal PtNum As String) As PartDocument
    Dim Prod As Product
    On Error Resume Next
        Set Prod = Prods.AddNewComponent("Part", PtNum)
    On Error GoTo 0
    Set Init_Part = Prods.item(Prods.Count).ReferenceProduct.Parent
End Function

Private Sub UpdateScene(ByVal Scene As Variant)
    Dim viewer As Viewer3D: Set viewer = CATIA.activeWindow.ActiveViewer
    Dim VPnt3D As Variant
    Set VPnt3D = viewer.Viewpoint3D
    Dim ary As Variant
    ary = GetRangeAry(Scene, 0, 2)
    Call VPnt3D.PutOrigin(ary)
    ary = GetRangeAry(Scene, 3, 5)
    Call VPnt3D.PutSightDirection(ary)
    ary = GetRangeAry(Scene, 6, 8)
    Call VPnt3D.PutUpDirection(ary)
    VPnt3D.FieldOfView = Scene(9)
    VPnt3D.FocusDistance = Scene(10)
    Call viewer.Update
End Sub

Private Function GetScene3D(ViewPnt3D As Viewpoint3D) As Variant
    Dim vp As Variant: Set vp = ViewPnt3D
    Dim origin(2) As Variant: Call vp.GetOrigin(origin)
    Dim sight(2) As Variant: Call vp.GetSightDirection(sight)
    GetScene3D = KCL.JoinAry(origin, sight)
    Dim up(2) As Variant: Call vp.GetUpDirection(up)
    GetScene3D = KCL.JoinAry(GetScene3D, up)
    Dim FieldOfView(0) As Variant: FieldOfView(0) = vp.FieldOfView
    GetScene3D = KCL.JoinAry(GetScene3D, FieldOfView)
    Dim FocusDist(0) As Variant: FocusDist(0) = vp.FocusDistance
    GetScene3D = KCL.JoinAry(GetScene3D, FocusDist)
End Function

Private Function GetViewPnt3D() As Viewpoint3D
    Set GetViewPnt3D = CATIA.activeWindow.ActiveViewer.Viewpoint3D
End Function

Attribute VB_Name = "m22_hasLeftAxis"
'Attribute VB_Name = "m2_hasLeftAxis"

' 检查零件文档中是否存在左手坐标系
'{Gp:999}
'{Ep:LeftHand}
'{Caption:LeftHandAxis}
'{ControlTipText:检查是否有左手坐标系}
'{BackColor:33023}
Option Explicit
Sub LeftHand()
    ' 检查是否可以执行
    If Not CanExecute("PartDocument") Then Exit Sub
    Dim doc As PartDocument: Set doc = CATIA.ActiveDocument
    Dim Axs As AxisSystems: Set Axs = doc.part.AxisSystems
    Dim Ax As AxisSystem
    Dim msg As String: msg = vbNullString
    For Each Ax In Axs
        If IsLeft(Ax) Then
            msg = msg & Ax.Name & vbNewLine
        End If
    Next
    If msg = vbNullString Then
        MsgBox "未找到左手坐标系。"
    Else
        MsgBox "已找到左手坐标系：" & vbNewLine & msg
    End If
End Sub

Private Function IsLeft(ByVal Ax As Variant) As Boolean
    ' 定义向量
    Dim VecX(2), VecY(2), VecZ(2)
    Ax.GetXAxis VecX
    Ax.GetYAxis VecY
    Ax.GetZAxis VecZ
    
    ' 计算 X 轴和 Y 轴的叉积
    Dim Outer(2) As Double
    Outer(0) = VecX(1) * VecY(2) - VecX(2) * VecY(1)
    Outer(1) = VecX(2) * VecY(0) - VecX(0) * VecY(2)
    Outer(2) = VecX(0) * VecY(1) - VecX(1) * VecY(0)
    
    ' 计算叉积结果与 Z 轴的点积，并判断是否小于 0
    IsLeft = _
        VecZ(0) * Outer(0) + VecZ(1) * Outer(1) + VecZ(2) * Outer(2) < 0
End Function

Attribute VB_Name = "m23_pt2xl"
'Attribute VB_Name = "m23_pt2xl"
' 点坐标的导出
'{GP:2}
'{EP:pt2xl}
'{Caption:批量点坐标}
'{ControlTipText: 提示选择几何图形集后导出下面的点集}
'{BackColor:}

Sub pt2xl()
    If Not CanExecute("PartDocument") Then
        Exit Sub
    End If
    Dim oDoc: Set oDoc = CATIA.ActiveDocument
    
    Dim HSF:  Set HSF = oDoc.part.HybridShapeFactory
    

    Dim HBS: Set HBS = oDoc.part.HybridBodies
    Dim osel: Set osel = oDoc.Selection
    
    '=======要求选择点集和坐标
    Dim imsg
    imsg = "请选择点所在的几何图形集"
    Dim oHb
    Set oHb = KCL.SelectItem(imsg, HybridBody)
    Dim oAxi
    imsg = "请再选择坐标系"
    Set oAxi = KCL.SelectItem(imsg, AxisSystem)
    
    If Not oHb Is Nothing Then
        Dim i, irow, ct
        
        Set oshapes = oHb.HybridShapes
        ct = oshapes.Count
        
        ReDim Arr(0 To ct, 0 To 4)
        irow = 0
        Arr(irow, 0) = "序号"
        Arr(irow, 1) = "名称"
        Arr(irow, 2) = "X"
        Arr(irow, 3) = "Y"
        Arr(irow, 4) = "Z"
        
        irow = 1
        
        ReDim fincoord(2), absCoord(2)
        
        For i = 1 To ct
            Set oPt = oshapes.item(i)
            Dim Str
            Str = HSF.GetGeometricalFeatureType(oPt)
            If Str = 1 Then
                Dim fakept
                Set fakept = HSF.AddNewPointCoordWithReference(0, 0, 0, oPt)
                oHb.AppendHybridShape fakept
                oDoc.part.Update
               fakept.GetCoordinates absCoord
               
                  osel.Clear
                  osel.Add fakept
                  osel.Delete
                  oDoc.part.Update
                If Not oAxi Is Nothing Then
                    fincoord = TransAxi(absCoord, oAxi)
                Else
                 fincoord = absCoord
                End If
                Arr(irow, 0) = irow
                Arr(irow, 1) = oPt.Name
                Arr(irow, 2) = fincoord(0)
                Arr(irow, 3) = fincoord(1)
                Arr(irow, 4) = fincoord(2)
                irow = irow + 1
            End If
        Next
        ArrayToxl Arr
    Else
        MsgBox "缺少待操作几何图形集，请检查选择"
        Exit Sub
    End If
End Sub

Sub ArrayToxl(arr2D() As Variant)
    Dim xlAPP
    Set xlAPP = CreateObject("Excel.Application")
    Dim wbook
    Set wbook = xlAPP.Workbooks.Add
    Dim rng
    Set rng = wbook.Sheets(1).Range("B2")
    With rng.Resize(UBound(arr2D, 1) + 1, UBound(arr2D, 2) + 1)
        .Value = arr2D
        .Borders.LineStyle = xlContinuous
        .Borders.Weight = xlThin
        .Borders.ColorIndex = 0
    End With
    xlAPP.Visible = True
End Sub
Function TransAxi(acoor As Variant, axi1) As Variant
    Dim origin(2), xDir(2), yDir(2), zDir(2)
    Dim i
    axi1.GetOrigin origin
    axi1.GetXAxis xDir
    axi1.GetYAxis yDir
    axi1.GetZAxis zDir
    Dim v(2) As Double
    For i = 0 To 2
        v(i) = acoor(i) - origin(i)
    Next
    Dim result(2)
    result(0) = v(0) * xDir(0) + v(1) * xDir(1) + v(2) * xDir(2)
    result(1) = v(0) * yDir(0) + v(1) * yDir(1) + v(2) * yDir(2)
    result(2) = v(0) * zDir(0) + v(1) * zDir(1) + v(2) * zDir(2)
    TransAxi = result
End Function
' = 0 , Unknown
' = 1 , Point
' = 2 , Curve
' = 3 , Line
' = 4 , Circle
' = 5 , Surface
' = 6 , Plane
' = 7 , Solid, Volume

Attribute VB_Name = "m23_pt2xl1"
'Attribute VB_Name = "m23_pt2xl"
' 点坐标的导出
'{GP:2}
'{EP:pt2xl}
'{Caption:批量点相对坐标}
'{ControlTipText: 提示选择几何图形集后导出下面的点集}
'{BackColor:12648447}

Sub pt2xl()

    If CATIA.Windows.Count < 1 Then
        MsgBox "没有打开的窗口"
        Exit Sub
    End If
    
    Dim oDoc
    On Error Resume Next
        Set oDoc = CATIA.ActiveDocument
    On Error GoTo 0
    Dim Str
    Str = TypeName(oDoc)
    If Not Str = "PartDocument" Then
    MsgBox "没有打开的part"
    Exit Sub
    End If
    
    
    Dim HSF:  Set HSF = oDoc.part.HybridShapeFactory
    Dim HBS: Set HBS = oDoc.part.HybridBodies
    Dim osel: Set osel = oDoc.Selection
    osel.Clear
    
    '=======要求选择点集和坐标
    Dim imsg, filter(0)
    imsg = "请选择点所在的几何图形集"
    filter(0) = "HybridBody"
    
    Set oHb = mysel(imsg, filter).Value
   
    Dim oAxi
    imsg = "请再选择坐标系"
    filter(0) = "AxisSystem"
    Set oAxi = mysel(imsg, filter).Value
     If Not oHb Is Nothing Then
        Dim i, irow, ct
        Set oshapes = oHb.HybridShapes
        ct = oshapes.Count
        ReDim Arr(0 To ct, 0 To 4)
        irow = 0
        Arr(irow, 0) = "序号"
        Arr(irow, 1) = "名称"
        Arr(irow, 2) = "X"
        Arr(irow, 3) = "Y"
        Arr(irow, 4) = "Z"
        irow = 1
         ReDim fincoord(2), absCoord(2)
        
        For i = 1 To ct
            Set oPt = oshapes.item(i)
   
            Str = HSF.GetGeometricalFeatureType(oPt)
            If Str = 1 Then
                Dim fakept
                Set fakept = HSF.AddNewPointCoordWithReference(0, 0, 0, oPt)
                oHb.AppendHybridShape fakept
                oDoc.part.Update
               fakept.GetCoordinates absCoord
               
                  osel.Clear
                  osel.Add fakept
                  osel.Delete
                  oDoc.part.Update
                If Not oAxi Is Nothing Then
                    fincoord = TransAxi(absCoord, oAxi)
                Else
                 fincoord = absCoord
                End If
                Arr(irow, 0) = irow
                Arr(irow, 1) = oPt.Name
                Arr(irow, 2) = fincoord(0)
                Arr(irow, 3) = fincoord(1)
                Arr(irow, 4) = fincoord(2)
                irow = irow + 1
            End If
        Next
        ArrayToxl Arr
    Else
        MsgBox "缺少待操作几何图形集，请检查选择"
        Exit Sub
    End If
End Sub

Sub ArrayToxl(arr2D() As Variant)
    Dim xlAPP
    Set xlAPP = CreateObject("Excel.Application")
    Dim wbook
    Set wbook = xlAPP.Workbooks.Add
    Dim rng
    Set rng = wbook.Sheets(1).Range("B2")
    With rng.Resize(UBound(arr2D, 1) + 1, UBound(arr2D, 2) + 1)
        .Value = arr2D
        .Borders.LineStyle = xlContinuous
        .Borders.Weight = xlThin
        .Borders.ColorIndex = 0
    End With
    xlAPP.Visible = True
End Sub
Function TransAxi(acoor As Variant, axi1) As Variant
    Dim origin(2), xDir(2), yDir(2), zDir(2)
    Dim i
    axi1.GetOrigin origin
    axi1.GetXAxis xDir
    axi1.GetYAxis yDir
    axi1.GetZAxis zDir
    Dim v(2) As Double
    For i = 0 To 2
        v(i) = acoor(i) - origin(i)
    Next
    Dim result(2)
    result(0) = v(0) * xDir(0) + v(1) * xDir(1) + v(2) * xDir(2)
    result(1) = v(0) * yDir(0) + v(1) * yDir(1) + v(2) * yDir(2)
    result(2) = v(0) * zDir(0) + v(1) * zDir(1) + v(2) * zDir(2)
    TransAxi = result
End Function

Function mysel(prompt, filter())
    Dim osel
    Set osel = CATIA.ActiveDocument.Selection
    osel.Clear
    Dim iType(0)
'
'    Dim status
'    status = osel.SelectElement2(filter, prompt, False)

    If osel.SelectElement2(filter, prompt, False) = "Normal" Then
        If osel.Count = 1 Then
            Set mysel = osel.item(1)
        End If
    Else
    Set mysel = Nothing
    End If
    osel.Clear
End Function
' = 0 , Unknown
' = 1 , Point
' = 2 , Curve
' = 3 , Line
' = 4 , Circle
' = 5 , Surface
' = 6 , Plane
' = 7 , Solid, Volume

Attribute VB_Name = "m24_wfrename"
'Attribute VB_Name = "m24_wfrename"
' 重命名几何元素
'{GP:2}
'{EP:wfrename}
'{Caption:几何重命名}
'{ControlTipText: 提示选择几何图形集后导出下面的点集}
'{BackColor:12648447}
' = 0 , Unknown
' = 1 , Point
' = 2 , Curve
' = 3 , Line
' = 4 , Circle
' = 5 , Surface
' = 6 , Plane
' = 7 , Solid, Volume

Sub wfrename()
   
  If CATIA.Windows.Count < 1 Then
        MsgBox "没有打开的窗口"
        Exit Sub
    End If
    
    Dim oDoc
    On Error Resume Next
        Set oDoc = CATIA.ActiveDocument
    On Error GoTo 0
    Dim Str
    Str = TypeName(oDoc)
    If Not Str = "PartDocument" Then
    MsgBox "没有打开的part"
    Exit Sub
    End If
 

End Sub

Attribute VB_Name = "m31_reorderPrd"
'Attribute VB_Name = "sample_ReOrder_Product"
'{GP:3}
'{Ep:CATMain}
'{Caption:产品排序}
'{ControlTipText:产品排序}
'{BackColor: }
Option Explicit
Sub CATMain()
    If Not CanExecute("ProductDocument") Then Exit Sub
    Dim ProDoc As productDocument: Set ProDoc = CATIA.ActiveDocument
    Dim Pros As Products: Set Pros = ProDoc.Product.Products
    If Pros.Count < 2 Then Exit Sub
    Dim AssyMode As AsmConstraintSettingAtt
    Set AssyMode = CATIA.SettingControllers.item("CATAsmConstraintSettingCtrl")
    Dim OriginalMode As CatAsmPasteComponentMode
    OriginalMode = AssyMode.PasteComponentMode
    AssyMode.PasteComponentMode = catPasteWithCstOnCopyAndCut
    Dim Names: Set Names = Get_SortedNames(Pros)
    Dim sel As Selection: Set sel = ProDoc.Selection
    Dim Itm As Variant
    CATIA.HSOSynchronized = False
    sel.Clear
    For Each Itm In Names
        sel.Add Pros.item(Itm)
    Next
    sel.Cut
    With sel
        .Clear
        .Add Pros
        .Paste
        .Clear
    End With
    CATIA.HSOSynchronized = True
    AssyMode.PasteComponentMode = OriginalMode
    ProDoc.Product.Update
End Sub
Private Function Get_SortedNames(ByVal Pros As Products) As Object
    Dim lst As Object
    Set lst = KCL.InitLst()
    Dim Pro As Product
    For Each Pro In Pros
        lst.Add Pro.Name
    Next
    lst.Sort
    Set Get_SortedNames = lst
End Function

Attribute VB_Name = "m32_weldSel"
'Attribute VB_Name = "weldSel"
'{GP:3==}
'{Ep:CATMain}
'{Caption:产品焊缝}
'{ControlTipText:选择被连接的产品}
'{BackColor:}

Sub CATMain()
If Not KCL.CanExecute("ProductDocument") Then Exit Sub
MsgBox "还没编呢"
'
'Set Doc = CATIA.ActiveDocument
'Set rootPrd = Doc.Product
'Set sPrd = rootPrd.Products
'Set iprd = sPrd.item("点焊信息")
'Set osel = Doc.Selection
'Dim oPn
'Dim iType(0)
'osel.Clear
'iType(0) = "Product"
'status = osel.SelectElement3(iType, "选择被连接产品", True, 2, False)
'If status = "Normal" And osel.Count2 <= 3 Then
'oName = ""
'For i = 1 To osel.Count
'     oPn = oPn & "_" & osel.item(i).LeafProduct.PartNumber
'Next
' iPn = "SotWeld_" & oPn
'     MsgBox iPn
'End If
'Set oprd = iprd.Products.AddNewComponent("Part", "")
'oprd.PartNumber = iPn
'osel.Clear
End Sub

Attribute VB_Name = "m33_Updateme"
'Attribute VB_Name = "m33_Updateme"
'{GP:3}
'{Ep:Upall}
'{Caption:更新零件}
'{ControlTipText:遍历结构树并更新}
'{BackColor:}

Sub Upall()

    Dim part
    Dim doc
    For Each doc In CATIA.Documents
        If TypeName(doc) = "PartDocument" Then
            Set part = doc.part
            Exit For
        End If
    Next


'tosave =doc.saved
'if tosave =false then


    For Each doc In CATIA.Documents
      isupdated = True
      If TypeName(doc) = "PartDocument" Then
          isupdated = part.isupdate(doc.part)
          ElseIf TypeName(doc) = "ProductDocument" Then
          isupdated = part.IsUpToDate(doc.Product)
      End If


    If Not isupdated Then
        On Error Resume Next
        doc.part.Update
        doc.Product.Update
        doc.Product.referenceprodcut.Parent.Update
    End If
    
    Next

End Sub

Attribute VB_Name = "m34_sendDir"
'Attribute VB_Name = "m34_sendDir"
'{GP:3}
'{Ep:sendDir}
'{Caption:备份到路径}
'{ControlTipText:send当前根产品到路径}
'{BackColor:}

Sub sendDir()
    CATIA.DisplayFileAlerts = True
    Dim oDoc
    Set oDoc = CATIA.ActiveDocument
    dpath = oDoc.path
    dName = oDoc.Name
    initial = dpath & "\" & dName
    
    Dim pn
    If KCL.IsType_Of_T(oDoc, "DrawingDocument") Then
        pn = strbflast(oDoc.Name, ".")
    Else
        pn = oDoc.Product.PartNumber
    End If
    
    fname = rmchn(pn)    '将所有中文字符替换为&
        
    Dim bckFolderName As String
    bckFolderName = KCL.strbflast(fname, "_") & "_" & KCL.timestamp("min")
    
    Dim opath
    opath = KCL.ofParentPath(dpath)
    
    bckFolder = opath & bckFolderName
    If Not KCL.isPathchn(bckFolder) Then
        Set Send = CATIA.CreateSendTo()
        Send.KeepDirectory (1)  '1 keepdir ， 0 no keep dir
        Send.SetInitialFile initial
        Send.SetDirectoryFile bckFolder
        Send.Run
        MsgBox "已经备份到" & bckFolder
        
    Else
        MsgBox bckFolder & vbNewLine & _
        "  " & vbNewLine & _
         "你的产品零件号包含非法字符，无法备份，请检查!"
    End If
End Sub


Function rmchn(inputString) As String
    Dim regEx: Set regEx = CreateObject("VBScript.RegExp")
    regEx.Pattern = "[\u4e00-\u9fa5]"
    regEx.Global = True
    rmchn = regEx.Replace(inputString, " ")
    Set regEx = Nothing
End Function
Sub mdlog()
    Dim oDoc, currPath
    Set oDoc = CATIA.ActiveDocument
    currPath = IIf(oDoc.path = "", "", oDoc.path)
    mdpath = currPath & ".md"
End Sub

Attribute VB_Name = "m35_ex2stp"
'Attribute VB_Name = "m35_ex2stp"
' 导出stp并压缩为压缩包
'{GP:3}
'{EP:ex2stp_zip}
'{Caption:导出stp}
'{ControlTipText: 一键导出stp并压缩到指定路径或本身目录}
'{BackColor:}
' 定义模块级变量
Private errorMessage As String

Sub ex2stp_zip()
    On Error Resume Next ' 临时开启错误处理
    If Not CanExecute("ProductDocument") Then
       errorMessage = "当前文档类型不支持此操作。"
        GoTo ShowMessage
    End If
    
    Dim oDoc As Document
    Set oDoc = CATIA.ActiveDocument
    
    Dim outputpath As String
    askdir.Show
    outputpath = GetOutputPath(oDoc)
    
    If outputpath = "" Then
        errorMessage = "缺少导出路径，操作取消！"
        GoTo ShowMessage
    Else
        Dim pn: pn = oDoc.Product.PartNumber
        If dt_pth_ctrl(0) = 1 Then
            Dim ttp: ttp = KCL.timestamp(dt_pth_ctrl(1))
            oDoc.Product.PartNumber = KCL.strbflast(pn, "_") & ttp ' 零件号更新
        End If

        stpname = KCL.strbf1st(oDoc.Product.PartNumber, "_") & "_Housing_" & ttp
        
        Dim stpfilepath As String
        Dim opath(2) '0=路径，1=name，2=extname
            opath(0) = outputpath
            opath(1) = stpname
            opath(2) = "stp"
        stpfilepath = KCL.JoinPathName(opath)
        
        MsgBox stpfilepath
        '================导出stp
        oDoc.ExportData stpfilepath, "stp"
        If Err.Number <> 0 Then
            errorMessage = "STP 导出失败：" & Err.Description
            GoTo ShowMessage
        End If
        '================检查文件存在性
        
                If Not KCL.isExists(stpfilepath) Then
                    errorMessage = "STP 文件导出后未找到：" & stpfilepath
                    GoTo ShowMessage
                End If
                If Not ex2zip(stpfilepath) Then
                    GoTo ShowMessage
                 End If
        KCL.DeleteMe stpfilepath ' 删除原始 STP 文件
    End If

ShowMessage:
    If errorMessage <> "" Then
        MsgBox errorMessage, vbCritical
    Else
        MsgBox stpfilepath & ".zip文件已压缩,STP 原始文件已删除。", vbInformation
    End If
    
    Set oDoc = Nothing
    On Error GoTo 0 ' 关闭错误处理
    errorMessage = "" ' 重置错误信息
End Sub

Function ex2zip(oFilepath) As Boolean
    Dim zipPath, result, shell, cmd, path7z
    path7z = "D:\for use\7-Zip\7z.exe"
    If KCL.isExists(path7z) Then
        zipPath = oFilepath & ".7z" ' 构建 7z 压缩包路径
        cmd = """" & path7z & """ a -t7z -mx=9 """ & zipPath & """ """ & oFilepath & """"
    Else
        zipPath = oFilepath & ".zip" ' 构建 ZIP 压缩包路径
        cmd = "powershell -Command ""Compress-Archive -Path '""" & oFilepath & """' -DestinationPath '""" & zipPath & """' -CompressionLevel Optimal -Force"""
    End If
    Set shell = CreateObject("WScript.Shell")
    result = shell.Run(cmd, 0, True)
    If result <> 0 Then
        errorMessage = "压缩失败！请确保 PowerShell 版本不低于 5.0 或 7-Zip 已经安装。"
        ex2zip = False
    Else
        If Not KCL.isExists(zipPath) Then
            errorMessage = "压缩完成但未找到压缩文件！"
            ex2zip = False
        Else
        
      
            ex2zip = True
            
              cmd = "explorer.exe /select, """ & zipPath & """"
        shell.Run (cmd)
        End If
    End If
End Function


Private Function GetOutputPath(ByVal doc As Document) As String
    Select Case dt_pth_ctrl(2)
        Case 0  ' 用户选择自定义路径
            Dim shellApp, folderBrowser
            Set shellApp = CreateObject("Shell.Application")
            Set folderBrowser = shellApp.BrowseForFolder(0, "选择STP输出文件夹", 16, 0)
            If Not folderBrowser Is Nothing Then
                GetOutputPath = folderBrowser.Self.path
            Else
              GetOutputPath = ""
            End If
        Case 1  ' 使用当前文档路径
            GetOutputPath = IIf(doc.path = "", "", doc.path)
        Case others ' 用户取消操作
            GetOutputPath = ""
    End Select
End Function

Attribute VB_Name = "m40_setgprd"
'{GP:4}
'{Ep:setgprd}
'{Caption:选择产品}
'{ControlTipText:选择要被读取或修改的产品}
'{BackColor:16744703}

Sub setgprd()
    If Not CanExecute("ProductDocument") Then Exit Sub
    If pdm Is Nothing Then
        Set pdm = New class_PDM
    End If

    Set gPrd = pdm.defgprd()
    Set ProductObserver.CurrentProduct = gPrd ' 这会自动触发事件
        If Not gPrd Is Nothing Then
           imsg = "你选择的产品是" & gPrd.PartNumber
            MsgBox imsg
        Else
             MsgBox "已退出，程序将结束"
        End If
End Sub

Attribute VB_Name = "m41_freegPrd"
'Attribute VB_Name = "selPrd"
'{GP:4}
'{Ep:freegprd}
'{Caption:释放产品}
'{ControlTipText:将待操作产品清空}
'{BackColor:16744703}


Sub freegprd()
    Set gPrd = Nothing

    Set ProductObserver.CurrentProduct = gPrd ' 这会自动触发事件
    MsgBox "已清空待操作产品"
    Call clearall
End Sub

Attribute VB_Name = "m42_readPrd"
'Attribute VB_Name = "ReadPrd"
'{gp:4}
'{Ep:readPrd}
'{Caption:读取属性}
'{ControlTipText:读取待操作产品}
'{BackColor: }

Sub readPrd()
    If pdm Is Nothing Then
     Set pdm = New class_PDM
    End If
 '---------获取待修改产品 '---------遍历修改产品及子产品
    If gPrd Is Nothing Then
         MsgBox "请先选择产品，程序将退出"
         Exit Sub
    Else
         If gws Is Nothing Then
           Set xlm = New Class_XLM
         End If
        
        gPrd.ApplyWorkMode (3)
        Dim currRow: currRow = 2
         
        Dim Prd2Read
        Set Prd2Read = gPrd
        If Not Prd2Read Is Nothing Then
            xlm.inject_data currRow, pdm.infoPrd(Prd2Read)
            Dim children
            Set children = Prd2Read.Products
            For i = 1 To children.Count
                currRow = i + 2
                xlm.inject_data currRow, pdm.infoPrd(children.item(i))
            Next
        End If
      End If
        Set Prd2Read = Nothing
End Sub

Attribute VB_Name = "m43_rvPrd"
'{GP:4}
'{Ep:rvme}
'{Caption:修改产品}
'{ControlTipText:选择要被读取或修改的产品}
'{BackColor: }

Sub rvme()
     If Not gPrd Is Nothing Then
        gPrd.ApplyWorkMode (3)
        Dim currRow: currRow = 2
        
'---------遍历修改产品及子产品   Set data =
        Dim Prd2rv
        Set Prd2rv = gPrd
        Dim odata As Variant
        
            odata = xlm.extract_data(currRow)
            Call pdm.modatt(Prd2rv, odata)
            
        Dim children
            Set children = Prd2rv.Products
            
        If children.Count > 0 Then
            For i = 1 To children.Count
                currRow = currRow + 1
                Dim sdata As Variant
                sdata = xlm.extract_data(currRow)
                Call pdm.modatt(children.item(i), sdata)
            Next
        End If
        
            Set Prd2rv = Nothing
        MsgBox "已经修改产品"
    Else
        MsgBox "请先选择产品，程序将退出"
        Exit Sub
     End If
    On Error GoTo 0

End Sub


Public Function extract_data(indRow)

    Dim iCols
    iCols = Array(0, 2, 4, 6, 8, 10, 12)

    
     Set ws = xlAPP.ActiveSheet
     
    
    Dim temparr As Variant
    
    temparr = ws.Rows(indRow).Resize(1, 14).Value
    

    Dim outputArr As Variant
    Dim j As Long
    ReDim outputArr(1 To UBound(iCols))
    For j = 1 To UBound(iCols)
         outputArr(j) = ""
         If IsEmpty(temparr(1, iCols(j))) = False Then
         outputArr(j) = temparr(1, iCols(j))
         End If
    Next
    extract_data = outputArr ' 返回提取的数据
End Function

Attribute VB_Name = "m45_initme"
'Attribute VB_Name = "initme"
'{GP:4}
'{Ep:initme}
'{Caption:初始化模板}
'{ControlTipText:将选择的产品和子产品文档按模板格式化}
'{BackColor: }

Sub initme()



 
 If KCL.CanExecute("ProductDocument") Then
     If pdm Is Nothing Then
       Set pdm = New class_PDM
     End If
     Set allPN = KCL.InitDic(vbTextCompare)
     allPN.RemoveAll
    Dim iprd: Set iprd = pdm.defgprd()
    If Not iprd Is Nothing Then
        On Error Resume Next
           Call ini_oPrd(iprd)
             allPN.RemoveAll
            
                 If Error.Number = 0 Then
                        MsgBox "零件模板已经应用"
                     Else
                     MsgBox "至少一个参数创建错误，请检查lisence"
                 End If
        On Error GoTo 0
    End If
    
    
Else
 On Error Resume Next
    If KCL.CanExecute("PartDocument") Then
      Set oprd = CATIA.ActiveDocument.Product
      If pdm Is Nothing Then
                Set pdm = New class_PDM
           End If
      Call pdm.initPrd(oprd)
    If Error.Number = 0 Then
            MsgBox "零件模板已经应用"
            Else
            MsgBox "至少一个参数创建错误，请检查lisence"
          End If
      On Error GoTo 0
End If
End If

End Sub
Sub ini_oPrd(oprd)
        If allPN.Exists(oprd.PartNumber) = False Then
            allPN(oprd.PartNumber) = 1
            Call pdm.initPrd(oprd)
        End If
            For Each Product In oprd.Products
                Call ini_oPrd(Product)
        Next
End Sub

Attribute VB_Name = "m51_Cal_Mass"
'{GP:5}
'{Ep:Cal_Mass}
'{Caption:迭代重量}
'{ControlTipText:选择要被读取或修改的产品}
'{BackColor:}

Sub Cal_Mass()
    If Not KCL.CanExecute("ProductDocument") Then Exit Sub

    If pdm Is Nothing Then
        Set pdm = New class_PDM
    End If
   On Error Resume Next
            If Not gPrd Is Nothing Then
                Call pdm.Assmass(gPrd)
            Else
                Call setgprd
                Err.Clear
                Call pdm.Assmass(gPrd)
            End If
            
   If Err.Number > 0 Then
        MsgBox "程序错误,请确认零件模板是否应用：" & Err.Description, vbCritical
   Else
            MsgBox "重量已计算"
    End If


End Sub

Attribute VB_Name = "m52_LV2_Mass"
'{GP:5}
'{Ep:L2Mass}
'{Caption:迭代重量L2}
'{ControlTipText:只计算第二级产品重量}
'{BackColor:}

Sub L2Mass()
    If Not KCL.CanExecute("ProductDocument") Then Exit Sub
    If pdm Is Nothing Then
        Set pdm = New class_PDM
    End If
    If gPrd Is Nothing Then
        Call setgprd
    End If
   Set oprd = gPrd
   Call cal2mass(oprd, 1)
    Set oprd = Nothing
End Sub
Function cal2mass(oprd, LV)
If LV <= 3 Then
            Set children = oprd.Products
            If children.Count > 0 Then
                For i = 1 To children.Count
                    Call cal2mass(children.item(i), LV + 1)
                    total = total + children.item(i).ReferenceProduct.UserRefProperties.item("Mass").Value
                Next
                    oprd.ReferenceProduct.UserRefProperties.item("Mass").Value = total
            Else
                    total = oprd.ReferenceProduct.UserRefProperties.item("Mass").Value
            End If
    End If
End Function

Attribute VB_Name = "m53_Cbom"
'{GP:5}
'{Ep:cBom}
'{Caption:生成BOM}
'{ControlTipText:选择要被读取或修改的产品}
'{BackColor:16744703}

Sub cBom()
If Not KCL.CanExecute("ProductDocument") Then Exit Sub
     If pdm Is Nothing Then
          Set pdm = New class_PDM
     End If
     If gPrd Is Nothing Then
    
     Set gPrd = pdm.defgprd()
    Set ProductObserver.CurrentProduct = gPrd ' 这会自动触发事件
      End If
      
    If gws Is Nothing Then
     Set xlm = New Class_XLM
    End If
      Set iprd = gPrd
            counter = 1
          If Not iprd Is Nothing Then
          xlm.inject_bom pdm.recurPrd(iprd, 1)
     End If
     Set iprd = Nothing
     xlm.freesheet
     
End Sub

Attribute VB_Name = "m54_cGXBOM"
'{GP:5}
'{Ep:cgxBom}
'{Caption:GXBOM}
'{ControlTipText:选择要被读取或修改的产品}
'{BackColor:16744703}

Sub cgxBom()
If Not KCL.CanExecute("ProductDocument") Then Exit Sub
     If pdm Is Nothing Then
          Set pdm = New class_PDM
     End If
     If gPrd Is Nothing Then
    
     Set gPrd = pdm.defgprd()
    Set ProductObserver.CurrentProduct = gPrd ' 这会自动触发事件
      End If
      
    If gws Is Nothing Then
     Set xlm = New Class_XLM
    End If
      Set iprd = gPrd
            counter = 1
          If Not iprd Is Nothing Then
          xlm.inject_gxbom pdm.gxBom(iprd, 1)
     End If
     Set iprd = Nothing
     xlm.freesheet
     
End Sub

Attribute VB_Name = "m62_shot"
'Attribute VB_Name = "m5_Cbom"
'{GP:6==}
'{Ep:shot}
'{Caption:截图到文件夹}
'{ControlTipText:选择要被读取或修改的产品}
'{BackColor:16744703}

Sub shot()

MsgBox "没编呢"
Exit Sub

 Dim iprd, rootprd, oprd, children
 Dim xlsht, rng, RC(0 To 1), oArry()
 Dim i, oRowNb
  RC(0) = 3: RC(1) = 3
    On Error Resume Next
    Set CATIA = GetObject(, "CATIA.Application") '获取catia程序
    Dim oDoc: Set oDoc = CATIA.ActiveDocument
    Set rootprd = CATIA.ActiveDocument.Product
         If Err.Number <> 0 Then
            MsgBox "请打开CATIA并打开你的产品，再运行本程序": Err.Clear
            Exit Sub
         End If
    On Error GoTo 0
    Set xlAPP = GetObject(, "Excel.Application") '获取excel程序
    Set xlsht = xlAPP.ActiveSheet: xlsht.Columns(2).NumberFormatLocal = "0.000"

Dim oWindow, oViewer
Dim file_type As String
Set oWindow = CATIA.activeWindow
oWindow.Layout = catWindowGeomOnly
Set oViewer = oWindow.ActiveViewer
oViewer.Reframe

'====修改背景颜色=====
Dim MyViewer, oColor(2)
Set MyViewer = CATIA.activeWindow.ActiveViewer
MyViewer.GetBackgroundColor oColor
MyViewer.PutBackgroundColor Array(1, 1, 1) ' Change background color to WHITE

'====修改背景颜色=====
file_type = "tiff"
Dim oName, CapturePath, oType
  CapturePath = CATIA.FileSelectionBox("输入文件名", file_type, CatFileSelectionModeSave)
  oName = CapturePath & "." & file_type
oType = catCaptureFormatTIFF 'catCaptureFormatBMP catCaptureFormatJPEG
MyViewer.CaptureToFile oType, oName ' MAIN SENTENCE!! STORE THE PICTURE IN ANY FORMAT
MyViewer.PutBackgroundColor oColor ' Change background original
MsgBox ("已经保存图片")
oWindow.Layout = catWindowSpecsAndGeom 'catWindowSpecsOnly ' catWindowGeomOnly

End Sub
Function shotme()

    Dim iprd, rootprd, oprd, children
    Dim xlsht, rng, RC(0 To 1), oArry()
    Dim i, oRowNb
     RC(0) = 3: RC(1) = 3
       On Error Resume Next
       Set CATIA = GetObject(, "CATIA.Application") '获取catia程序
       Dim oDoc: Set oDoc = CATIA.ActiveDocument
       Set rootprd = CATIA.ActiveDocument.Product
            If Err.Number <> 0 Then
               MsgBox "请打开CATIA并打开你的产品，再运行本程序": Err.Clear
               Exit Sub
            End If
    On Error GoTo 0
    Set xlAPP = GetObject(, "Excel.Application") '获取excel程序
    Set xlsht = xlAPP.ActiveSheet: xlsht.Columns(2).NumberFormatLocal = "0.000"

    Dim oWindow, oViewer
    Dim file_type As String
    Set oWindow = CATIA.activeWindow
    oWindow.Layout = catWindowGeomOnly
    Set oViewer = oWindow.ActiveViewer
    oViewer.Reframe

'====修改背景颜色=====
    Dim MyViewer, oColor(2)
    Set MyViewer = CATIA.activeWindow.ActiveViewer
    MyViewer.GetBackgroundColor oColor
    MyViewer.PutBackgroundColor Array(1, 1, 1) ' Change background color to WHITE

'====修改背景颜色=====
    file_type = "tiff"
    
    Dim oName, CapturePath, oType
    
    
    MyViewer.CaptureToClipboard
    
      CapturePath = CATIA.FileSelectionBox("输入文件名", file_type, CatFileSelectionModeSave)
      oName = CapturePath & "." & file_type
      
    oType = catCaptureFormatTIFF 'catCaptureFormatBMP catCaptureFormatJPEG
    
    MyViewer.CaptureToFile oType, oName ' MAIN SENTENCE!! STORE THE PICTURE IN ANY FORMAT
    
    MyViewer.PutBackgroundColor oColor ' Change background original
    
    MsgBox ("已经保存图片")
    oWindow.Layout = catWindowSpecsAndGeom 'catWindowSpecsOnly ' catWindowGeomOnly



End Function

Attribute VB_Name = "m63_NewTree"
'Attribute VB_Name = "m30_NewTree"
'{GP:6}
'{Ep:CATMain}
'{Caption:新电池箱体}
'{ControlTipText:新建一个电池箱体的结构树}
'{BackColor:}
Private Tree As Variant
Private prj
Sub CATMain()
        Dim oprd, Tree, oDoc, rootprd, cover, house, ref
          Dim imsg
          imsg = "请输入你的项目名称"
        prj = GetInput(imsg)
        If prj = "" Then
            Exit Sub
        End If
        Set Tree = KCL.InitDic(vbTextCompare)
        Call iniTree(Tree)
        '====创建参考和包络===
    For i = 0 To 18
        Select Case i
            Case 0      '创建根产品
                Set oDoc = CATIA.Documents.Add("Product")
                Set rootprd = oDoc.Product
                Set oprd = rootprd
            Case 1
                Set oprd = rootprd.Products.AddNewComponent("Product", "")
            Case 2
                 Set oprd = rootprd.Products.AddNewComponent("Product", "")
            Case 3      '创建上箱体组件
                Set cover = rootprd.Products.AddNewComponent("Product", "")
                Set oprd = cover
           Case 4     '创建上箱体
                Set oprd = cover.Products.AddNewComponent("Part", "")
           Case 5     '创建下箱体
                Set house = rootprd.Products.AddNewComponent("Product", "")
                Set oprd = house
            Case 6 '创建参考件
                Set ref = house.Products.AddNewComponent("Part", "")
                Set oprd = ref
            Case 12, 13, 14 '创建零件
                Set oprd = house.Products.AddNewComponent("Part", "")
                oprd.Name = Tree(i)(4)
            Case 15, 16:
               Set oprd = house.Products.AddNewProduct("")
            Case 17
               Set oprd = rootprd.Products.AddNewComponent("Product", "")
            Case 18
                Set fast = rootprd.Products.AddNewComponent("Product", "")
                Set oprd = fast
        Case Else
                Set oprd = house.Products.AddNewComponent("Product", "")
        End Select
          Call newPn(oprd, Tree(i))
          Set oprd = Nothing
    Next
        '===新增component
     ' Set product4 = products1.AddNewProduct("")
    ' 新增产品= oprd.products.AddNewComponent("Part", "")
    Dim osel
    Set osel = CATIA.ActiveDocument.Selection
    osel.Clear
    osel.Add ref
    osel.Copy
    osel.Clear
    Dim otp
    Set otp = CATIA.ActiveDocument.Selection
    otp.Clear
    otp.Add fast
    otp.Paste
End Sub

Sub iniTree(Tree)
    Tree(0) = Array(0, "_Prj_Housing_Asm", "Project Housing Asm", "箱体组件", "Housing Asm")
    Tree(1) = Array(0, "_Pack", "Pack system", "整包方案", "Pack system")
    Tree(2) = Array(0, "_Packaging", "packaging", "包络定义", "packaging")
    Tree(3) = Array(0, "_000", "Upper Housing Asm", "上箱体总成", "Upper Housing Asm")
    Tree(4) = Array(0, "_001", "Upper Housing", "上箱体", "Upper Housing")
    Tree(5) = Array(0, "_1000", "Lower Housing Asm", "下箱体总成", "Lower Housing Asm")
    Tree(6) = Array(0, "_ref", "Ref", "参考", "Ref")
    Tree(7) = Array(0, "_1100", "Frames", "框架组件", "Frames")
    Tree(8) = Array(0, "_1200", "Members", "梁组件", "Members")
    Tree(9) = Array(0, "_1300", "Brkts", "支架组件", "Brkts")
    Tree(10) = Array(0, "_1400", "Bottom components", "底部组件", "Bottom components")
    Tree(11) = Array(0, "_1500", "Cooling system", "液冷组件", "Cooling system")
    Tree(12) = Array(0, "_2001", "Weldings Seams", "焊缝", "Weldings Seams")
    Tree(13) = Array(0, "_2002", "SPot Welding", "点焊", "Spot Welding")
    Tree(14) = Array(0, "_2003", "Adhesive", "胶水", "adhesive")
    
    Tree(15) = Array(0, "_4000", "Grou_fasteners", "紧固件组合", "Group_Fastener.1")
    Tree(16) = Array(0, "_5000", "others", "其他组件", "others")
    
    Tree(17) = Array(0, "_Abandon", "Abandoned", "废案", "Abandoned")
    Tree(18) = Array(0, "_Patterns", "Fasteners", "紧固件阵列", "Fasteners Pattern")
    
End Sub

Sub newPn(oprd, Arr)
    oprd.Name = Arr(4)
    oprd.PartNumber = prj & Arr(1)
    oprd.nomenclature = Arr(2)
    oprd.definition = Arr(3)
    On Error Resume Next
    oprd.Name = Arr(4)
    On Error GoTo 0
    oprd.Name = Arr(4)
    oprd.Update
End Sub

Public Function GetInput(msg) As String
    Dim UserInput As String
    UserInput = InputBox(msg, "输入提示")
    
    ' 如果用户没有输入或点击取消，则返回默认值"XX"
    If UserInput = "" Or UserInput = "0" Then
        GetInput = ""
    Else
        GetInput = UserInput
    End If
End Function

Attribute VB_Name = "m64_ivhideshow"
'Attribute VB_Name = "m64_hide&show"
'{GP:6}
'{Ep:CATMain}
'{Caption:反选隐藏}
'{ControlTipText:反选并隐藏结构树}
'{BackColor:}

Sub CATMain()
Dim oDoc
Set oDoc = CATIA.ActiveDocument
Dim cGroups
Set cGroups = oDoc.Product.GetTechnologicalObject("Groups")
Dim oGroup As Group
Set oGroup = cGroups.AddFromSel    ' 当前选择产品添加到组
oGroup.ExtractMode = 1
oGroup.FillSelWithInvert   '  反选
'oGroup.FillSelWithExtract
' Delete the group
  cGroups.Remove 1
  Set cGroups = Nothing
  Dim sel
Set sel = oDoc.Selection
Set VisPropertySet = sel.VisProperties
sel.VisProperties.SetShow 1  '' 将所有选中元素设置为不可见
'VisPropertySet.SetShow 0
End Sub

Attribute VB_Name = "rmusrPrp"
Sub CATMain()
Set oprd = CATIA.ActiveDocument.Product
rm oprd
End Sub
Sub rm(oprd)
    On Error Resume Next
     Set refPrd = oprd.ReferenceProduct
     Set oprt = refPrd.Parent.part
    Set colls = refPrd.Publications
    colls.Remove ("Location")
    colls.Remove ("iMass")
    colls.Remove ("iDensity")
    colls.Remove ("iThickness")
    colls.Remove ("iMaterial")
     Set colls = refPrd.Parent.part.Parameters.RootParameterSet.ParameterSets
        Set cm = colls.GetItem("cm")
        Set osel = CATIA.ActiveDocument.Selection
        osel.Clear
        osel.Add cm
        osel.Delete
                
     Set colls = refPrd.Parent.part.relations
     colls.Remove ("CalM")
     colls.Remove ("CMAS")
     colls.Remove ("CTK")
         
     Set colls = refPrd.UserRefProperties
     colls.Remove ("iMass")
     colls.Remove ("iMaterial")
     colls.Remove ("iThickness")
    If oprd.Products.Count > 0 Then
        For i = 1 To oprd.Products.Count
          rm (oprd.Products.item(i))
        Next
    End If
On Error GoTo 0
End Sub

Attribute VB_Name = "test"

#If VBA7 And Win64 Then
    Private Declare PtrSafe Function timeGetTime Lib "winmm.dll" () As Long
#Else
    Private Declare Function timeGetTime Lib "winmm.dll" () As Long
#End If
' 需要声明Windows API函数
#If VBA7 Then
    Private Declare PtrSafe Function OpenClipboard Lib "user32" (ByVal hwnd As LongPtr) As LongPtr
    Private Declare PtrSafe Function EmptyClipboard Lib "user32" () As LongPtr
    Private Declare PtrSafe Function CloseClipboard Lib "user32" () As LongPtr
    Private Declare PtrSafe Function SetClipboardData Lib "user32" (ByVal wFormat As Long, ByVal hMem As LongPtr) As LongPtr
    Private Declare PtrSafe Function CopyImage Lib "user32" (ByVal handle As LongPtr, ByVal un1 As Long, ByVal n1 As Long, ByVal n2 As Long, ByVal un2 As Long) As LongPtr
    Private Declare PtrSafe Function LoadImage Lib "user32" Alias "LoadImageA" (ByVal hInst As LongPtr, ByVal lpsz As String, ByVal un1 As Long, ByVal n1 As Long, ByVal n2 As Long, ByVal un2 As Long) As LongPtr
#Else
    Private Declare Function OpenClipboard Lib "user32" (ByVal hwnd As Long) As Long
    Private Declare Function EmptyClipboard Lib "user32" () As Long
    Private Declare Function CloseClipboard Lib "user32" () As Long
    Private Declare Function SetClipboardData Lib "user32" (ByVal wFormat As Long, ByVal hMem As Long) As Long
    Private Declare Function CopyImage Lib "user32" (ByVal handle As Long, ByVal un1 As Long, ByVal n1 As Long, ByVal n2 As Long, ByVal un2 As Long) As Long
    Private Declare Function LoadImage Lib "user32" Alias "LoadImageA" (ByVal hInst As Long, ByVal lpsz As String, ByVal un1 As Long, ByVal n1 As Long, ByVal n2 As Long, ByVal un2 As Long) As Long
#End If



Private mSW& ' 秒表开始时间

'Dim oDoc
'Dim CATIA, xlApp
'Public bomdata
'Public Att(1 To 4)
'Public aType(1 To 4)
Option Explicit

Sub test()
 If gws Is Nothing Then
   Set xlm = New Class_XLM
   
End If

Dim data(1 To 10, 1 To 15)

Dim i, j

For i = 1 To 10
    For j = 1 To 15
    data(i, j) = 99
    Next
Next

With gws

.Range(.Cells(1, 1), .Cells(10, 15)).Value = data

End With

End Sub
