Attribute VB_Name = "A00_backmeup"
Option Explicit
'
Private Const mdlname As String = "A00_backmeup"
Sub bckUp_Modules()
    Dim fm As New VbaModuleManegerView
    On Error Resume Next
        fm.Show
    On Error GoTo 0
End Sub
Public Sub AddmdlName()
    Dim vbComp As Object
    Dim codemod As Object
    Dim i As Long, startline As Long, prockind As Long
    Dim searchStartLine As Long, searchStartCol As Long
    Dim searchEndLine As Long, searchEndCol As Long
    Dim declText As String, constName As String, procName As String
    constName = "mdlname"
    Dim vbprj As Object: Set vbprj = KCL.GetApc().ExecutingProject.VBProject
    Dim colls: Set colls = vbprj.VBComponents
    For Each vbComp In colls
        Set codemod = vbComp.CodeModule
        For i = 1 To codemod.CountOfLines
            procName = codemod.ProcOfLine(i, prockind)
            If procName <> "" Then
                startline = codemod.ProcBodyLine(procName, prockind)
                searchStartLine = 1
                searchStartCol = 1
                searchEndLine = startline
                searchEndCol = -1
                declText = "Private Const " & constName & " As String = """ & vbComp.Name & """"
                ' Use variables for Find arguments
                If Not codemod.Find("Const " & constName, searchStartLine, searchStartCol, searchEndLine, searchEndCol) Then
                    codemod.InsertLines startline, declText
                Else
                    codemod.ReplaceLine searchStartLine, declText
                End If
                Exit For
            End If
        Next i
    Next vbComp
        MsgBox "added mdlname", vbInformation, "added mdlname"
End Sub

Attribute VB_Name = "Cls_JsonConverter"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Option Explicit

' === VBA-UTC Headers
#If Mac Then

#If VBA7 Then

' 64-bit Mac (2016)
Private Declare PtrSafe Function utc_popen Lib "/usr/lib/libc.dylib" Alias "popen" _
    (ByVal utc_Command As String, ByVal utc_Mode As String) As LongPtr
Private Declare PtrSafe Function utc_pclose Lib "/usr/lib/libc.dylib" Alias "pclose" _
    (ByVal utc_File As LongPtr) As LongPtr
Private Declare PtrSafe Function utc_fread Lib "/usr/lib/libc.dylib" Alias "fread" _
    (ByVal utc_Buffer As String, ByVal utc_Size As LongPtr, ByVal utc_Number As LongPtr, ByVal utc_File As LongPtr) As LongPtr
Private Declare PtrSafe Function utc_feof Lib "/usr/lib/libc.dylib" Alias "feof" _
    (ByVal utc_File As LongPtr) As LongPtr

#Else

' 32-bit Mac
Private Declare Function utc_popen Lib "libc.dylib" Alias "popen" _
    (ByVal utc_Command As String, ByVal utc_Mode As String) As Long
Private Declare Function utc_pclose Lib "libc.dylib" Alias "pclose" _
    (ByVal utc_File As Long) As Long
Private Declare Function utc_fread Lib "libc.dylib" Alias "fread" _
    (ByVal utc_Buffer As String, ByVal utc_Size As Long, ByVal utc_Number As Long, ByVal utc_File As Long) As Long
Private Declare Function utc_feof Lib "libc.dylib" Alias "feof" _
    (ByVal utc_File As Long) As Long

#End If

#ElseIf VBA7 Then

' http://msdn.microsoft.com/en-us/library/windows/desktop/ms724421.aspx
' http://msdn.microsoft.com/en-us/library/windows/desktop/ms724949.aspx
' http://msdn.microsoft.com/en-us/library/windows/desktop/ms725485.aspx
Private Declare PtrSafe Function utc_GetTimeZoneInformation Lib "kernel32" Alias "GetTimeZoneInformation" _
    (utc_lpTimeZoneInformation As utc_TIME_ZONE_INFORMATION) As Long
Private Declare PtrSafe Function utc_SystemTimeToTzSpecificLocalTime Lib "kernel32" Alias "SystemTimeToTzSpecificLocalTime" _
    (utc_lpTimeZoneInformation As utc_TIME_ZONE_INFORMATION, utc_lpUniversalTime As utc_SYSTEMTIME, utc_lpLocalTime As utc_SYSTEMTIME) As Long
Private Declare PtrSafe Function utc_TzSpecificLocalTimeToSystemTime Lib "kernel32" Alias "TzSpecificLocalTimeToSystemTime" _
    (utc_lpTimeZoneInformation As utc_TIME_ZONE_INFORMATION, utc_lpLocalTime As utc_SYSTEMTIME, utc_lpUniversalTime As utc_SYSTEMTIME) As Long

#Else

Private Declare Function utc_GetTimeZoneInformation Lib "kernel32" Alias "GetTimeZoneInformation" _
    (utc_lpTimeZoneInformation As utc_TIME_ZONE_INFORMATION) As Long
Private Declare Function utc_SystemTimeToTzSpecificLocalTime Lib "kernel32" Alias "SystemTimeToTzSpecificLocalTime" _
    (utc_lpTimeZoneInformation As utc_TIME_ZONE_INFORMATION, utc_lpUniversalTime As utc_SYSTEMTIME, utc_lpLocalTime As utc_SYSTEMTIME) As Long
Private Declare Function utc_TzSpecificLocalTimeToSystemTime Lib "kernel32" Alias "TzSpecificLocalTimeToSystemTime" _
    (utc_lpTimeZoneInformation As utc_TIME_ZONE_INFORMATION, utc_lpLocalTime As utc_SYSTEMTIME, utc_lpUniversalTime As utc_SYSTEMTIME) As Long

#End If

#If Mac Then

#If VBA7 Then
Private Type utc_ShellResult
    utc_Output As String
    utc_ExitCode As LongPtr
End Type

#Else

Private Type utc_ShellResult
    utc_Output As String
    utc_ExitCode As Long
End Type

#End If

#Else

Private Type utc_SYSTEMTIME
    utc_wYear As Integer
    utc_wMonth As Integer
    utc_wDayOfWeek As Integer
    utc_wDay As Integer
    utc_wHour As Integer
    utc_wMinute As Integer
    utc_wSecond As Integer
    utc_wMilliseconds As Integer
End Type

Private Type utc_TIME_ZONE_INFORMATION
    utc_Bias As Long
    utc_StandardName(0 To 31) As Integer
    utc_StandardDate As utc_SYSTEMTIME
    utc_StandardBias As Long
    utc_DaylightName(0 To 31) As Integer
    utc_DaylightDate As utc_SYSTEMTIME
    utc_DaylightBias As Long
End Type

#End If
' === End VBA-UTC

Private Type json_Options
    ' VBA only stores 15 significant digits, so any numbers larger than that are truncated
    ' This can lead to issues when BIGINT's are used (e.g. for Ids or Credit Cards), as they will be invalid above 15 digits
    ' See: http://support.microsoft.com/kb/269370
    '
    ' By default, VBA-JSON will use String for numbers longer than 15 characters that contain only digits
    ' to override set `JsonConverter.JsonOptions.UseDoubleForLargeNumbers = True`
    UseDoubleForLargeNumbers As Boolean

    ' The JSON standard reqDic_UI object keys to be quoted (" or '), use this option to allow unquoted keys
    AllowUnquotedKeys As Boolean

    ' The solidus (/) is not required to be escaped, use this option to escape them as \/ in ConvertToJson
    EscapeSolidus As Boolean
End Type
'Public JsonOptions As json_Options
Private JsonOptions As json_Options

' ============================================= '
' Public Methods
' ============================================= '

''
' Convert JSON string to object (Dictionary/Collection)
'
' @method ParseJson
' @param {String} json_String
' @return {Object} (Dictionary or Collection)
' @throws 10001 - JSON parse error
''
Private Const mdlname As String = "Cls_JsonConverter"
Public Function ParseJson(ByVal JsonString As String) As Object
    Dim json_Index As Long
    json_Index = 1

    ' Remove vbCr, vbLf, and vbTab from json_String
    JsonString = VBA.Replace(VBA.Replace(VBA.Replace(JsonString, VBA.vbCr, ""), VBA.vbLf, ""), VBA.vbTab, "")

    json_SkipSpaces JsonString, json_Index
    Select Case VBA.Mid$(JsonString, json_Index, 1)
    Case "{"
        Set ParseJson = json_ParseObject(JsonString, json_Index)
    Case "["
        Set ParseJson = json_ParseArray(JsonString, json_Index)
    Case Else
        ' Error: Invalid JSON string
        Err.Raise 10001, "JSONConverter", json_ParseErrorMessage(JsonString, json_Index, "Expecting '{' or '['")
    End Select
End Function

''
' Convert object (Dictionary/Collection/Array) to JSON
'
' @method ConvertToJson
' @param {Variant} JsonValue (Dictionary, Collection, or Array)
' @param {Integer|String} Whitespace "Pretty" print json with given number of spaces per indentation (Integer) or given string
' @return {String}
''
Public Function ConvertToJson(ByVal JsonValue As Variant, Optional ByVal Whitespace As Variant, Optional ByVal json_CurrentIndentation As Long = 0) As String
    Dim json_Buffer As String
    Dim json_BufferPosition As Long
    Dim json_BufferLength As Long
    Dim json_Index As Long
    Dim json_LBound As Long
    Dim json_UBound As Long
    Dim json_IsFirstItem As Boolean
    Dim json_Index2D As Long
    Dim json_LBound2D As Long
    Dim json_UBound2D As Long
    Dim json_IsFirstItem2D As Boolean
    Dim json_Key As Variant
    Dim json_Value As Variant
    Dim json_DateStr As String
    Dim json_Converted As String
    Dim json_SkipItem As Boolean
    Dim json_PrettyPrint As Boolean
    Dim json_Indentation As String
    Dim json_InnerIndentation As String

    json_LBound = -1
    json_UBound = -1
    json_IsFirstItem = True
    json_LBound2D = -1
    json_UBound2D = -1
    json_IsFirstItem2D = True
    json_PrettyPrint = Not IsMissing(Whitespace)

    Select Case VBA.VarType(JsonValue)
    Case VBA.vbNull
        ConvertToJson = "null"
    Case VBA.vbDate
        ' Date
        json_DateStr = ConvertToIso(VBA.CDate(JsonValue))

        ConvertToJson = """" & json_DateStr & """"
    Case VBA.vbString
        ' String (or large number encoded as string)
        If Not JsonOptions.UseDoubleForLargeNumbers And json_StringIsLargeNumber(JsonValue) Then
            ConvertToJson = JsonValue
        Else
            ConvertToJson = """" & json_Encode(JsonValue) & """"
        End If
    Case VBA.vbBoolean
        If JsonValue Then
            ConvertToJson = "true"
        Else
            ConvertToJson = "false"
        End If
    Case VBA.vbArray To VBA.vbArray + VBA.vbByte
        If json_PrettyPrint Then
            If VBA.VarType(Whitespace) = VBA.vbString Then
                json_Indentation = VBA.String$(json_CurrentIndentation + 1, Whitespace)
                json_InnerIndentation = VBA.String$(json_CurrentIndentation + 2, Whitespace)
            Else
                json_Indentation = VBA.Space$((json_CurrentIndentation + 1) * Whitespace)
                json_InnerIndentation = VBA.Space$((json_CurrentIndentation + 2) * Whitespace)
            End If
        End If

        ' Array
        json_BufferAppend json_Buffer, "[", json_BufferPosition, json_BufferLength

        On Error Resume Next

        json_LBound = LBound(JsonValue, 1)
        json_UBound = UBound(JsonValue, 1)
        json_LBound2D = LBound(JsonValue, 2)
        json_UBound2D = UBound(JsonValue, 2)

        If json_LBound >= 0 And json_UBound >= 0 Then
            For json_Index = json_LBound To json_UBound
                If json_IsFirstItem Then
                    json_IsFirstItem = False
                Else
                    ' Append comma to previous line
                    json_BufferAppend json_Buffer, ",", json_BufferPosition, json_BufferLength
                End If

                If json_LBound2D >= 0 And json_UBound2D >= 0 Then
                    ' 2D Array
                    If json_PrettyPrint Then
                        json_BufferAppend json_Buffer, vbNewLine, json_BufferPosition, json_BufferLength
                    End If
                    json_BufferAppend json_Buffer, json_Indentation & "[", json_BufferPosition, json_BufferLength

                    For json_Index2D = json_LBound2D To json_UBound2D
                        If json_IsFirstItem2D Then
                            json_IsFirstItem2D = False
                        Else
                            json_BufferAppend json_Buffer, ",", json_BufferPosition, json_BufferLength
                        End If

                        json_Converted = ConvertToJson(JsonValue(json_Index, json_Index2D), Whitespace, json_CurrentIndentation + 2)

                        ' For Arrays/Collections, undefined (Empty/Nothing) is treated as null
                        If json_Converted = "" Then
                            ' (nest to only check if converted = "")
                            If json_IsUndefined(JsonValue(json_Index, json_Index2D)) Then
                                json_Converted = "null"
                            End If
                        End If

                        If json_PrettyPrint Then
                            json_Converted = vbNewLine & json_InnerIndentation & json_Converted
                        End If

                        json_BufferAppend json_Buffer, json_Converted, json_BufferPosition, json_BufferLength
                    Next json_Index2D

                    If json_PrettyPrint Then
                        json_BufferAppend json_Buffer, vbNewLine, json_BufferPosition, json_BufferLength
                    End If

                    json_BufferAppend json_Buffer, json_Indentation & "]", json_BufferPosition, json_BufferLength
                    json_IsFirstItem2D = True
                Else
                    ' 1D Array
                    json_Converted = ConvertToJson(JsonValue(json_Index), Whitespace, json_CurrentIndentation + 1)

                    ' For Arrays/Collections, undefined (Empty/Nothing) is treated as null
                    If json_Converted = "" Then
                        ' (nest to only check if converted = "")
                        If json_IsUndefined(JsonValue(json_Index)) Then
                            json_Converted = "null"
                        End If
                    End If

                    If json_PrettyPrint Then
                        json_Converted = vbNewLine & json_Indentation & json_Converted
                    End If

                    json_BufferAppend json_Buffer, json_Converted, json_BufferPosition, json_BufferLength
                End If
            Next json_Index
        End If

        On Error GoTo 0

        If json_PrettyPrint Then
            json_BufferAppend json_Buffer, vbNewLine, json_BufferPosition, json_BufferLength

            If VBA.VarType(Whitespace) = VBA.vbString Then
                json_Indentation = VBA.String$(json_CurrentIndentation, Whitespace)
            Else
                json_Indentation = VBA.Space$(json_CurrentIndentation * Whitespace)
            End If
        End If

        json_BufferAppend json_Buffer, json_Indentation & "]", json_BufferPosition, json_BufferLength

        ConvertToJson = json_BufferToString(json_Buffer, json_BufferPosition)

    ' Dictionary or Collection
    Case VBA.vbObject
        If json_PrettyPrint Then
            If VBA.VarType(Whitespace) = VBA.vbString Then
                json_Indentation = VBA.String$(json_CurrentIndentation + 1, Whitespace)
            Else
                json_Indentation = VBA.Space$((json_CurrentIndentation + 1) * Whitespace)
            End If
        End If

        ' Dictionary
        If VBA.TypeName(JsonValue) = "Dictionary" Then
            json_BufferAppend json_Buffer, "{", json_BufferPosition, json_BufferLength
            For Each json_Key In JsonValue.keys
                ' For Objects, undefined (Empty/Nothing) is not added to object
                json_Converted = ConvertToJson(JsonValue(json_Key), Whitespace, json_CurrentIndentation + 1)
                If json_Converted = "" Then
                    json_SkipItem = json_IsUndefined(JsonValue(json_Key))
                Else
                    json_SkipItem = False
                End If

                If Not json_SkipItem Then
                    If json_IsFirstItem Then
                        json_IsFirstItem = False
                    Else
                        json_BufferAppend json_Buffer, ",", json_BufferPosition, json_BufferLength
                    End If

                    If json_PrettyPrint Then
                        json_Converted = vbNewLine & json_Indentation & """" & json_Key & """: " & json_Converted
                    Else
                        json_Converted = """" & json_Key & """:" & json_Converted
                    End If

                    json_BufferAppend json_Buffer, json_Converted, json_BufferPosition, json_BufferLength
                End If
            Next json_Key

            If json_PrettyPrint Then
                json_BufferAppend json_Buffer, vbNewLine, json_BufferPosition, json_BufferLength

                If VBA.VarType(Whitespace) = VBA.vbString Then
                    json_Indentation = VBA.String$(json_CurrentIndentation, Whitespace)
                Else
                    json_Indentation = VBA.Space$(json_CurrentIndentation * Whitespace)
                End If
            End If

            json_BufferAppend json_Buffer, json_Indentation & "}", json_BufferPosition, json_BufferLength

        ' Collection
        ElseIf VBA.TypeName(JsonValue) = "Collection" Then
            json_BufferAppend json_Buffer, "[", json_BufferPosition, json_BufferLength
            For Each json_Value In JsonValue
                If json_IsFirstItem Then
                    json_IsFirstItem = False
                Else
                    json_BufferAppend json_Buffer, ",", json_BufferPosition, json_BufferLength
                End If

                json_Converted = ConvertToJson(json_Value, Whitespace, json_CurrentIndentation + 1)

                ' For Arrays/Collections, undefined (Empty/Nothing) is treated as null
                If json_Converted = "" Then
                    ' (nest to only check if converted = "")
                    If json_IsUndefined(json_Value) Then
                        json_Converted = "null"
                    End If
                End If

                If json_PrettyPrint Then
                    json_Converted = vbNewLine & json_Indentation & json_Converted
                End If

                json_BufferAppend json_Buffer, json_Converted, json_BufferPosition, json_BufferLength
            Next json_Value

            If json_PrettyPrint Then
                json_BufferAppend json_Buffer, vbNewLine, json_BufferPosition, json_BufferLength

                If VBA.VarType(Whitespace) = VBA.vbString Then
                    json_Indentation = VBA.String$(json_CurrentIndentation, Whitespace)
                Else
                    json_Indentation = VBA.Space$(json_CurrentIndentation * Whitespace)
                End If
            End If

            json_BufferAppend json_Buffer, json_Indentation & "]", json_BufferPosition, json_BufferLength
        End If

        ConvertToJson = json_BufferToString(json_Buffer, json_BufferPosition)
    Case VBA.vbInteger, VBA.vbLong, VBA.vbSingle, VBA.vbDouble, VBA.vbCurrency, VBA.vbDecimal
        ' Number (use decimals for numbers)
        ConvertToJson = VBA.Replace(JsonValue, ",", ".")
    Case Else
        ' vbEmpty, vbError, vbDataObject, vbByte, vbUserDefinedType
        ' Use VBA's built-in to-string
        On Error Resume Next
        ConvertToJson = JsonValue
        On Error GoTo 0
    End Select
End Function

' ============================================= '
' Private Functions
' ============================================= '

Private Function json_ParseObject(json_String As String, ByRef json_Index As Long) As Object ' Dictionary
    Dim json_Key As String
    Dim json_NextChar As String

    Set json_ParseObject = CreateObject("Scripting.Dictionary") 'New Dictionary
    json_SkipSpaces json_String, json_Index
    If VBA.Mid$(json_String, json_Index, 1) <> "{" Then
        Err.Raise 10001, "JSONConverter", json_ParseErrorMessage(json_String, json_Index, "Expecting '{'")
    Else
        json_Index = json_Index + 1

        Do
            json_SkipSpaces json_String, json_Index
            If VBA.Mid$(json_String, json_Index, 1) = "}" Then
                json_Index = json_Index + 1
                Exit Function
            ElseIf VBA.Mid$(json_String, json_Index, 1) = "," Then
                json_Index = json_Index + 1
                json_SkipSpaces json_String, json_Index
            End If

            json_Key = json_ParseKey(json_String, json_Index)
            json_NextChar = json_Peek(json_String, json_Index)
            If json_NextChar = "[" Or json_NextChar = "{" Then
                Set json_ParseObject.item(json_Key) = json_ParseValue(json_String, json_Index)
            Else
                json_ParseObject.item(json_Key) = json_ParseValue(json_String, json_Index)
            End If
        Loop
    End If
End Function

Private Function json_ParseArray(json_String As String, ByRef json_Index As Long) As Collection
    Set json_ParseArray = New Collection

    json_SkipSpaces json_String, json_Index
    If VBA.Mid$(json_String, json_Index, 1) <> "[" Then
        Err.Raise 10001, "JSONConverter", json_ParseErrorMessage(json_String, json_Index, "Expecting '['")
    Else
        json_Index = json_Index + 1

        Do
            json_SkipSpaces json_String, json_Index
            If VBA.Mid$(json_String, json_Index, 1) = "]" Then
                json_Index = json_Index + 1
                Exit Function
            ElseIf VBA.Mid$(json_String, json_Index, 1) = "," Then
                json_Index = json_Index + 1
                json_SkipSpaces json_String, json_Index
            End If

            json_ParseArray.Add json_ParseValue(json_String, json_Index)
        Loop
    End If
End Function

Private Function json_ParseValue(json_String As String, ByRef json_Index As Long) As Variant
    json_SkipSpaces json_String, json_Index
    Select Case VBA.Mid$(json_String, json_Index, 1)
    Case "{"
        Set json_ParseValue = json_ParseObject(json_String, json_Index)
    Case "["
        Set json_ParseValue = json_ParseArray(json_String, json_Index)
    Case """", "'"
        json_ParseValue = json_ParseString(json_String, json_Index)
    Case Else
        If VBA.Mid$(json_String, json_Index, 4) = "true" Then
            json_ParseValue = True
            json_Index = json_Index + 4
        ElseIf VBA.Mid$(json_String, json_Index, 5) = "false" Then
            json_ParseValue = False
            json_Index = json_Index + 5
        ElseIf VBA.Mid$(json_String, json_Index, 4) = "null" Then
            json_ParseValue = Null
            json_Index = json_Index + 4
        ElseIf VBA.InStr("+-0123456789", VBA.Mid$(json_String, json_Index, 1)) Then
            json_ParseValue = json_ParseNumber(json_String, json_Index)
        Else
            Err.Raise 10001, "JSONConverter", json_ParseErrorMessage(json_String, json_Index, "Expecting 'STRING', 'NUMBER', null, true, false, '{', or '['")
        End If
    End Select
End Function

Private Function json_ParseString(json_String As String, ByRef json_Index As Long) As String
    Dim json_Quote As String
    Dim json_Char As String
    Dim json_Code As String
    Dim json_Buffer As String
    Dim json_BufferPosition As Long
    Dim json_BufferLength As Long

    json_SkipSpaces json_String, json_Index

    ' Store opening quote to look for matching closing quote
    json_Quote = VBA.Mid$(json_String, json_Index, 1)
    json_Index = json_Index + 1

    Do While json_Index > 0 And json_Index <= Len(json_String)
        json_Char = VBA.Mid$(json_String, json_Index, 1)

        Select Case json_Char
'        Case "\\"
'            Stop
        Case "\"
            ' Escaped string, \\, or \/
            json_Index = json_Index + 1
            json_Char = VBA.Mid$(json_String, json_Index, 1)

            Select Case json_Char
'            Case "\"
'                json_BufferAppend json_Buffer, json_Char & json_Char, json_BufferPosition, json_BufferLength
'                json_Index = json_Index + 1
            Case """", "\", "/", "'"
'            Case """", "/", "'"
                json_BufferAppend json_Buffer, json_Char, json_BufferPosition, json_BufferLength
                json_Index = json_Index + 1
            Case "b"
                json_BufferAppend json_Buffer, vbBack, json_BufferPosition, json_BufferLength
                json_Index = json_Index + 1
            Case "f"
                json_BufferAppend json_Buffer, vbFormFeed, json_BufferPosition, json_BufferLength
                json_Index = json_Index + 1
            Case "n"
                json_BufferAppend json_Buffer, vbCrLf, json_BufferPosition, json_BufferLength
                json_Index = json_Index + 1
            Case "r"
                json_BufferAppend json_Buffer, vbCr, json_BufferPosition, json_BufferLength
                json_Index = json_Index + 1
            Case "t"
                json_BufferAppend json_Buffer, vbTab, json_BufferPosition, json_BufferLength
                json_Index = json_Index + 1
            Case "u"
                ' Unicode character escape (e.g. \u00a9 = Copyright)
                json_Index = json_Index + 1
                json_Code = VBA.Mid$(json_String, json_Index, 4)
                json_BufferAppend json_Buffer, VBA.ChrW(VBA.val("&h" + json_Code)), json_BufferPosition, json_BufferLength
                json_Index = json_Index + 4
            End Select
        Case json_Quote
            json_ParseString = json_BufferToString(json_Buffer, json_BufferPosition)
            json_Index = json_Index + 1
            Exit Function
        Case Else
            json_BufferAppend json_Buffer, json_Char, json_BufferPosition, json_BufferLength
            json_Index = json_Index + 1
        End Select
    Loop
End Function

Private Function json_ParseNumber(json_String As String, ByRef json_Index As Long) As Variant
    Dim json_Char As String
    Dim json_Value As String
    Dim json_IsLargeNumber As Boolean

    json_SkipSpaces json_String, json_Index

    Do While json_Index > 0 And json_Index <= Len(json_String)
        json_Char = VBA.Mid$(json_String, json_Index, 1)

        If VBA.InStr("+-0123456789.eE", json_Char) Then
            ' Unlikely to have massive number, so use simple append rather than buffer here
            json_Value = json_Value & json_Char
            json_Index = json_Index + 1
        Else
            ' Excel only stores 15 significant digits, so any numbers larger than that are truncated
            ' This can lead to issues when BIGINT's are used (e.g. for Ids or Credit Cards), as they will be invalid above 15 digits
            ' See: http://support.microsoft.com/kb/269370
            '
            ' Fix: Parse -> String, Convert -> String longer than 15/16 characters containing only numbers and decimal points -> Number
            ' (decimal doesn't factor into significant digit count, so if present check for 15 digits + decimal = 16)
            json_IsLargeNumber = IIf(InStr(json_Value, "."), Len(json_Value) >= 17, Len(json_Value) >= 16)
            If Not JsonOptions.UseDoubleForLargeNumbers And json_IsLargeNumber Then
                json_ParseNumber = json_Value
            Else
                ' VBA.Val does not use regional settings, so guard for comma is not needed
                json_ParseNumber = VBA.val(json_Value)
            End If
            Exit Function
        End If
    Loop
End Function

Private Function json_ParseKey(json_String As String, ByRef json_Index As Long) As String
    ' Parse key with single or double quotes
    If VBA.Mid$(json_String, json_Index, 1) = """" Or VBA.Mid$(json_String, json_Index, 1) = "'" Then
        json_ParseKey = json_ParseString(json_String, json_Index)
    ElseIf JsonOptions.AllowUnquotedKeys Then
        Dim json_Char As String
        Do While json_Index > 0 And json_Index <= Len(json_String)
            json_Char = VBA.Mid$(json_String, json_Index, 1)
            If (json_Char <> " ") And (json_Char <> ":") Then
                json_ParseKey = json_ParseKey & json_Char
                json_Index = json_Index + 1
            Else
                Exit Do
            End If
        Loop
    Else
        Err.Raise 10001, "JSONConverter", json_ParseErrorMessage(json_String, json_Index, "Expecting '""' or '''")
    End If

    ' Check for colon and skip if present or throw if not present
    json_SkipSpaces json_String, json_Index
    If VBA.Mid$(json_String, json_Index, 1) <> ":" Then
        Err.Raise 10001, "JSONConverter", json_ParseErrorMessage(json_String, json_Index, "Expecting ':'")
    Else
        json_Index = json_Index + 1
    End If
End Function

Private Function json_IsUndefined(ByVal json_Value As Variant) As Boolean
    ' Empty / Nothing -> undefined
    Select Case VBA.VarType(json_Value)
    Case VBA.vbEmpty
        json_IsUndefined = True
    Case VBA.vbObject
        Select Case VBA.TypeName(json_Value)
        Case "Empty", "Nothing"
            json_IsUndefined = True
        End Select
    End Select
End Function

Private Function json_Encode(ByVal json_Text As Variant) As String
    ' Reference: http://www.ietf.org/rfc/rfc4627.txt
    ' Escape: ", \, /, backspace, form feed, line feed, carriage return, tab
    Dim json_Index As Long
    Dim json_Char As String
    Dim json_AscCode As Long
    Dim json_Buffer As String
    Dim json_BufferPosition As Long
    Dim json_BufferLength As Long

    For json_Index = 1 To VBA.Len(json_Text)
        json_Char = VBA.Mid$(json_Text, json_Index, 1)
        json_AscCode = VBA.AscW(json_Char)

        ' When AscW returns a negative number, it returns the twos complement form of that number.
        ' To convert the twos complement notation into normal binary notation, add 0xFFF to the return result.
        ' https://support.microsoft.com/en-us/kb/272138
        If json_AscCode < 0 Then
            json_AscCode = json_AscCode + 65536
        End If

        ' From spec, ", \, and control characters must be escaped (solidus is optional)

        Select Case json_AscCode
        Case 34
            ' " -> 34 -> \"
            json_Char = "\"""
        Case 92
            ' \ -> 92 -> \\
            json_Char = "\\"
        Case 47
            ' / -> 47 -> \/ (optional)
            If JsonOptions.EscapeSolidus Then
                json_Char = "\/"
            End If
        Case 8
            ' backspace -> 8 -> \b
            json_Char = "\b"
        Case 12
            ' form feed -> 12 -> \f
            json_Char = "\f"
        Case 10
            ' line feed -> 10 -> \n
            json_Char = "\n"
        Case 13
            ' carriage return -> 13 -> \r
            json_Char = "\r"
        Case 9
            ' tab -> 9 -> \t
            json_Char = "\t"
        Case 0 To 31, 127 To 65535
            ' Non-ascii characters -> convert to 4-digit hex
            json_Char = "\u" & VBA.Right$("0000" & VBA.Hex$(json_AscCode), 4)
        End Select

        json_BufferAppend json_Buffer, json_Char, json_BufferPosition, json_BufferLength
    Next json_Index

    json_Encode = json_BufferToString(json_Buffer, json_BufferPosition)
End Function

Private Function json_Peek(json_String As String, ByVal json_Index As Long, Optional json_NumberOfCharacters As Long = 1) As String
    ' "Peek" at the next number of characters without incrementing json_Index (ByVal instead of ByRef)
    json_SkipSpaces json_String, json_Index
    json_Peek = VBA.Mid$(json_String, json_Index, json_NumberOfCharacters)
End Function

Private Sub json_SkipSpaces(json_String As String, ByRef json_Index As Long)
    ' Increment index to skip over spaces
    Do While json_Index > 0 And json_Index <= VBA.Len(json_String) And VBA.Mid$(json_String, json_Index, 1) = " "
        json_Index = json_Index + 1
    Loop
End Sub

Private Function json_StringIsLargeNumber(json_String As Variant) As Boolean
    ' Check if the given string is considered a "large number"
    ' (See json_ParseNumber)

    Dim json_Length As Long
    Dim json_CharIndex As Long
    json_Length = VBA.Len(json_String)

    ' Length with be at least 16 characters and assume will be less than 100 characters
    If json_Length >= 16 And json_Length <= 100 Then
        Dim json_CharCode As String

        json_StringIsLargeNumber = True

        For json_CharIndex = 1 To json_Length
            json_CharCode = VBA.Asc(VBA.Mid$(json_String, json_CharIndex, 1))
            Select Case json_CharCode
            ' Look for .|0-9|E|e
            Case 46, 48 To 57, 69, 101
                ' Continue through characters
            Case Else
                json_StringIsLargeNumber = False
                Exit Function
            End Select
        Next json_CharIndex
    End If
End Function

Private Function json_ParseErrorMessage(json_String As String, ByRef json_Index As Long, ErrorMessage As String)
    ' Provide detailed parse error message, including details of where and what occurred
    '
    ' Example:
    ' Error parsing JSON:
    ' {"abcde":True}
    '          ^
    ' Expecting 'STRING', 'NUMBER', null, true, false, '{', or '['

    Dim json_StartIndex As Long
    Dim json_StopIndex As Long

    ' Include 10 characters before and after error (if possible)
    json_StartIndex = json_Index - 10
    json_StopIndex = json_Index + 10
    If json_StartIndex <= 0 Then
        json_StartIndex = 1
    End If
    If json_StopIndex > VBA.Len(json_String) Then
        json_StopIndex = VBA.Len(json_String)
    End If

    json_ParseErrorMessage = "Error parsing JSON:" & VBA.vbNewLine & _
                             VBA.Mid$(json_String, json_StartIndex, json_StopIndex - json_StartIndex + 1) & VBA.vbNewLine & _
                             VBA.Space$(json_Index - json_StartIndex) & "^" & VBA.vbNewLine & _
                             ErrorMessage
End Function

Private Sub json_BufferAppend(ByRef json_Buffer As String, _
                              ByRef json_Append As Variant, _
                              ByRef json_BufferPosition As Long, _
                              ByRef json_BufferLength As Long)
    ' VBA can be slow to append strings due to allocating a new string for each append
    ' Instead of using the traditional append, allocate a large empty string and then copy string at append position
    '
    ' Example:
    ' Buffer: "abc  "
    ' Append: "def"
    ' Buffer Position: 3
    ' Buffer Length: 5
    '
    ' Buffer position + Append length > Buffer length -> Append chunk of blank space to buffer
    ' Buffer: "abc       "
    ' Buffer Length: 10
    '
    ' Put "def" into buffer at position 3 (0-based)
    ' Buffer: "abcdef    "
    '
    ' Approach based on cStringBuilder from vbAccelerator
    ' http://www.vbaccelerator.com/home/VB/Code/Techniques/RunTime_Debug_Tracing/VB6_Tracer_Utility_zip_cStringBuilder_cls.asp
    '
    ' and clsStringAppend from Philip Swannell
    ' https://github.com/VBA-tools/VBA-JSON/pull/82

    Dim json_AppendLength As Long
    Dim json_LengthPlusPosition As Long

    json_AppendLength = VBA.Len(json_Append)
    json_LengthPlusPosition = json_AppendLength + json_BufferPosition

    If json_LengthPlusPosition > json_BufferLength Then
        ' Appending would overflow buffer, add chunk
        ' (double buffer length or append length, whichever is bigger)
        Dim json_AddedLength As Long
        json_AddedLength = IIf(json_AppendLength > json_BufferLength, json_AppendLength, json_BufferLength)

        json_Buffer = json_Buffer & VBA.Space$(json_AddedLength)
        json_BufferLength = json_BufferLength + json_AddedLength
    End If

    ' Note: Namespacing with VBA.Mid$ doesn't work properly here, throwing compile error:
    ' Function call on left-hand side of assignment must return Variant or Object
    Mid$(json_Buffer, json_BufferPosition + 1, json_AppendLength) = CStr(json_Append)
    json_BufferPosition = json_BufferPosition + json_AppendLength
End Sub

Private Function json_BufferToString(ByRef json_Buffer As String, ByVal json_BufferPosition As Long) As String
    If json_BufferPosition > 0 Then
        json_BufferToString = VBA.Left$(json_Buffer, json_BufferPosition)
    End If
End Function

''
' VBA-UTC v1.0.6
' (c) Tim Hall - https://github.com/VBA-tools/VBA-UtcConverter
'
' UTC/ISO 8601 Converter for VBA
'
' Errors:
' 10011 - UTC parsing error
' 10012 - UTC conversion error
' 10013 - ISO 8601 parsing error
' 10014 - ISO 8601 conversion error
'
' @module UtcConverter
' @author tim.hall.engr@gmail.com
' @license MIT (http://www.opensource.org/licenses/mit-license.php)
'' ~~~~~~~~~~~~~~~~~~~~~~~~~~~~~~~~~~~~~~~~~~~~~~~~~~~~~~~~~~~~~~~~~~~~~~ '

' (Declarations moved to top)

' ============================================= '
' Public Methods
' ============================================= '

''
' Parse UTC date to local date
'
' @method ParseUtc
' @param {Date} UtcDate
' @return {Date} Local date
' @throws 10011 - UTC parsing error
''
Public Function ParseUtc(utc_UtcDate As Date) As Date
    On Error GoTo utc_ErrorHandling

#If Mac Then
    ParseUtc = utc_ConvertDate(utc_UtcDate)
#Else
    Dim utc_TimeZoneInfo As utc_TIME_ZONE_INFORMATION
    Dim utc_LocalDate As utc_SYSTEMTIME

    utc_GetTimeZoneInformation utc_TimeZoneInfo
    utc_SystemTimeToTzSpecificLocalTime utc_TimeZoneInfo, utc_DateToSystemTime(utc_UtcDate), utc_LocalDate

    ParseUtc = utc_SystemTimeToDate(utc_LocalDate)
#End If

    Exit Function

utc_ErrorHandling:
    Err.Raise 10011, "UtcConverter.ParseUtc", "UTC parsing error: " & Err.Number & " - " & Err.Description
End Function

''
' Convert local date to UTC date
'
' @method ConvertToUrc
' @param {Date} utc_LocalDate
' @return {Date} UTC date
' @throws 10012 - UTC conversion error
''
Public Function ConvertToUtc(utc_LocalDate As Date) As Date
    On Error GoTo utc_ErrorHandling

#If Mac Then
    ConvertToUtc = utc_ConvertDate(utc_LocalDate, utc_ConvertToUtc:=True)
#Else
    Dim utc_TimeZoneInfo As utc_TIME_ZONE_INFORMATION
    Dim utc_UtcDate As utc_SYSTEMTIME

    utc_GetTimeZoneInformation utc_TimeZoneInfo
    utc_TzSpecificLocalTimeToSystemTime utc_TimeZoneInfo, utc_DateToSystemTime(utc_LocalDate), utc_UtcDate

    ConvertToUtc = utc_SystemTimeToDate(utc_UtcDate)
#End If

    Exit Function

utc_ErrorHandling:
    Err.Raise 10012, "UtcConverter.ConvertToUtc", "UTC conversion error: " & Err.Number & " - " & Err.Description
End Function

''
' Parse ISO 8601 date string to local date
'
' @method ParseIso
' @param {Date} utc_IsoString
' @return {Date} Local date
' @throws 10013 - ISO 8601 parsing error
''
Public Function ParseIso(utc_IsoString As String) As Date
    On Error GoTo utc_ErrorHandling

    Dim utc_Parts() As String
    Dim utc_DateParts() As String
    Dim utc_TimeParts() As String
    Dim utc_OffsetIndex As Long
    Dim utc_HasOffset As Boolean
    Dim utc_NegativeOffset As Boolean
    Dim utc_OffsetParts() As String
    Dim utc_Offset As Date

    utc_Parts = VBA.Split(utc_IsoString, "T")
    utc_DateParts = VBA.Split(utc_Parts(0), "-")
    ParseIso = VBA.DateSerial(VBA.CInt(utc_DateParts(0)), VBA.CInt(utc_DateParts(1)), VBA.CInt(utc_DateParts(2)))

    If UBound(utc_Parts) > 0 Then
        If VBA.InStr(utc_Parts(1), "Z") Then
            utc_TimeParts = VBA.Split(VBA.Replace(utc_Parts(1), "Z", ""), ":")
        Else
            utc_OffsetIndex = VBA.InStr(1, utc_Parts(1), "+")
            If utc_OffsetIndex = 0 Then
                utc_NegativeOffset = True
                utc_OffsetIndex = VBA.InStr(1, utc_Parts(1), "-")
            End If

            If utc_OffsetIndex > 0 Then
                utc_HasOffset = True
                utc_TimeParts = VBA.Split(VBA.Left$(utc_Parts(1), utc_OffsetIndex - 1), ":")
                utc_OffsetParts = VBA.Split(VBA.Right$(utc_Parts(1), Len(utc_Parts(1)) - utc_OffsetIndex), ":")

                Select Case UBound(utc_OffsetParts)
                Case 0
                    utc_Offset = TimeSerial(VBA.CInt(utc_OffsetParts(0)), 0, 0)
                Case 1
                    utc_Offset = TimeSerial(VBA.CInt(utc_OffsetParts(0)), VBA.CInt(utc_OffsetParts(1)), 0)
                Case 2
                    ' VBA.Val does not use regional settings, use for seconds to avoid decimal/comma issues
                    utc_Offset = TimeSerial(VBA.CInt(utc_OffsetParts(0)), VBA.CInt(utc_OffsetParts(1)), Int(VBA.val(utc_OffsetParts(2))))
                End Select

                If utc_NegativeOffset Then: utc_Offset = -utc_Offset
            Else
                utc_TimeParts = VBA.Split(utc_Parts(1), ":")
            End If
        End If

        Select Case UBound(utc_TimeParts)
        Case 0
            ParseIso = ParseIso + VBA.TimeSerial(VBA.CInt(utc_TimeParts(0)), 0, 0)
        Case 1
            ParseIso = ParseIso + VBA.TimeSerial(VBA.CInt(utc_TimeParts(0)), VBA.CInt(utc_TimeParts(1)), 0)
        Case 2
            ' VBA.Val does not use regional settings, use for seconds to avoid decimal/comma issues
            ParseIso = ParseIso + VBA.TimeSerial(VBA.CInt(utc_TimeParts(0)), VBA.CInt(utc_TimeParts(1)), Int(VBA.val(utc_TimeParts(2))))
        End Select

        ParseIso = ParseUtc(ParseIso)

        If utc_HasOffset Then
            ParseIso = ParseIso - utc_Offset
        End If
    End If

    Exit Function

utc_ErrorHandling:
    Err.Raise 10013, "UtcConverter.ParseIso", "ISO 8601 parsing error for " & utc_IsoString & ": " & Err.Number & " - " & Err.Description
End Function

''
' Convert local date to ISO 8601 string
'
' @method ConvertToIso
' @param {Date} utc_LocalDate
' @return {Date} ISO 8601 string
' @throws 10014 - ISO 8601 conversion error
''
Public Function ConvertToIso(utc_LocalDate As Date) As String
    On Error GoTo utc_ErrorHandling

    ConvertToIso = VBA.Format$(ConvertToUtc(utc_LocalDate), "yyyy-mm-ddTHH:mm:ss.000Z")

    Exit Function

utc_ErrorHandling:
    Err.Raise 10014, "UtcConverter.ConvertToIso", "ISO 8601 conversion error: " & Err.Number & " - " & Err.Description
End Function

' ============================================= '
' Private Functions
' ============================================= '

#If Mac Then

Private Function utc_ConvertDate(utc_Value As Date, Optional utc_ConvertToUtc As Boolean = False) As Date
    Dim utc_ShellCommand As String
    Dim utc_Result As utc_ShellResult
    Dim utc_Parts() As String
    Dim utc_DateParts() As String
    Dim utc_TimeParts() As String

    If utc_ConvertToUtc Then
        utc_ShellCommand = "date -ur `date -jf '%Y-%m-%d %H:%M:%S' " & _
            "'" & VBA.Format$(utc_Value, "yyyy-mm-dd HH:mm:ss") & "' " & _
            " +'%s'` +'%Y-%m-%d %H:%M:%S'"
    Else
        utc_ShellCommand = "date -jf '%Y-%m-%d %H:%M:%S %z' " & _
            "'" & VBA.Format$(utc_Value, "yyyy-mm-dd HH:mm:ss") & " +0000' " & _
            "+'%Y-%m-%d %H:%M:%S'"
    End If

    utc_Result = utc_ExecuteInShell(utc_ShellCommand)

    If utc_Result.utc_Output = "" Then
        Err.Raise 10015, "UtcConverter.utc_ConvertDate", "'date' command failed"
    Else
        utc_Parts = Split(utc_Result.utc_Output, " ")
        utc_DateParts = Split(utc_Parts(0), "-")
        utc_TimeParts = Split(utc_Parts(1), ":")

        utc_ConvertDate = DateSerial(utc_DateParts(0), utc_DateParts(1), utc_DateParts(2)) + _
            TimeSerial(utc_TimeParts(0), utc_TimeParts(1), utc_TimeParts(2))
    End If
End Function

Private Function utc_ExecuteInShell(utc_ShellCommand As String) As utc_ShellResult
#If VBA7 Then
    Dim utc_File As LongPtr
    Dim utc_Read As LongPtr
#Else
    Dim utc_File As Long
    Dim utc_Read As Long
#End If

    Dim utc_Chunk As String

    On Error GoTo utc_ErrorHandling
    utc_File = utc_popen(utc_ShellCommand, "r")

    If utc_File = 0 Then: Exit Function

    Do While utc_feof(utc_File) = 0
        utc_Chunk = VBA.Space$(50)
        utc_Read = CLng(utc_fread(utc_Chunk, 1, Len(utc_Chunk) - 1, utc_File))
        If utc_Read > 0 Then
            utc_Chunk = VBA.Left$(utc_Chunk, CLng(utc_Read))
            utc_ExecuteInShell.utc_Output = utc_ExecuteInShell.utc_Output & utc_Chunk
        End If
    Loop

utc_ErrorHandling:
    utc_ExecuteInShell.utc_ExitCode = CLng(utc_pclose(utc_File))
End Function

#Else

Private Function utc_DateToSystemTime(utc_Value As Date) As utc_SYSTEMTIME
    utc_DateToSystemTime.utc_wYear = VBA.Year(utc_Value)
    utc_DateToSystemTime.utc_wMonth = VBA.Month(utc_Value)
    utc_DateToSystemTime.utc_wDay = VBA.Day(utc_Value)
    utc_DateToSystemTime.utc_wHour = VBA.Hour(utc_Value)
    utc_DateToSystemTime.utc_wMinute = VBA.Minute(utc_Value)
    utc_DateToSystemTime.utc_wSecond = VBA.Second(utc_Value)
    utc_DateToSystemTime.utc_wMilliseconds = 0
End Function

Private Function utc_SystemTimeToDate(utc_Value As utc_SYSTEMTIME) As Date
    utc_SystemTimeToDate = DateSerial(utc_Value.utc_wYear, utc_Value.utc_wMonth, utc_Value.utc_wDay) + _
        TimeSerial(utc_Value.utc_wHour, utc_Value.utc_wMinute, utc_Value.utc_wSecond)
End Function

#End If

Attribute VB_Name = "Cls_VbaMdlMgr"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


Option Explicit
Private Const DEBUG_MODE = False                        '调试模式
Private Const APP_NAME = "ModuleBridge"                 '应用名称
Private Const VERSION = "0.0.6"                         '版本
Private Const THIS_PROJECT_NAME = "VBAproject1" '"ModuleBridgeProject" '此项目名
Private Const USER_JSON_NAME = "user_data.json"         '数据保存文件名
Private Const SEPARATOR = "|"                           '路径分隔符-VBA-JSON对策
Private Const SOURCE_FOLDER_NAME = "Src"             '在CATVBA内创建时的文件夹
Private mVbe As Object                                  'VBA编辑器
Private mUtil As Cls_VbaUltiliseLib                       '工具类
Private mProjectLst As Collection                       '项目列表
Private mUserDict As Object                             '用户数据字典
Private mJson As Cls_JsonConverter                       'Json解析器
Private Const mdlname As String = "Cls_VbaMdlMgr"
Private Sub Class_Initialize()
    Set mUtil = New Cls_VbaUltiliseLib
    mUtil.DebugMode = DEBUG_MODE
    Set mVbe = mUtil.GetVbe()
    Set mJson = New Cls_JsonConverter
    Set mProjectLst = get_project_list()
    Set mUserDict = get_user_data()
End Sub
Private Sub Class_Terminate()
    Dim path As String
    path = get_this_dir_path() & "\" & USER_JSON_NAME
    Call cleanUp_userdata
    save_json path, mUserDict
End Sub
'***属性***
'应用标题
Property Get Title() As String
    Title = APP_NAME & " Ver" & VERSION
End Property
'此项目名
Property Get project_name() As String
   project_name = THIS_PROJECT_NAME
End Property
'***方法***
'获取项目
'return:VBProject集合
Function get_project_list() As Collection
    Dim lst As Collection
    Set lst = New Collection
    Dim proj As Object
    For Each proj In mVbe.vBProjects
        lst.Add proj
    Next
    Set get_project_list = lst
End Function
'获取项目名
'return:项目名
Function get_project_name_list() As Collection
    Dim lst As Collection
    Set lst = New Collection
    Dim proj As Object
    For Each proj In mProjectLst
        lst.Add proj.Name
    Next
    Set get_project_name_list = lst
End Function
'获取项目内的模块
'param: projectIdx-项目索引
'return: 模块集合
Function get_module_list( _
        ByVal projectIdx As Long) As Collection
    Dim lst As Collection
    Set lst = New Collection
    Set get_module_list = lst
    Dim proj As Object
    On Error Resume Next
        Set proj = mProjectLst.item(projectIdx)
    On Error GoTo 0
    If proj Is Nothing Then Exit Function
    Dim comp As Object
    For Each comp In proj.VBComponents
        If is_target_module_type(comp) Then
            lst.Add comp
        End If
    Next
End Function
'获取项目内的模块名
'param: projectIdx-项目索引
'return: 模块名集合
Function get_module_name_list( _
        ByVal projectIdx As Long) As Collection
    Dim lst As Collection
    Set lst = New Collection
    Set get_module_name_list = lst
    Dim comp As Object
    For Each comp In get_module_list(projectIdx)
        If is_target_module_type(comp) Then
            lst.Add comp.Name
        End If
    Next
End Function
'获取指定模块内函数名列表
'param: comp-模块
'return: 函数名字符串
Private Function get_fanction_names( _
        ByVal comp As Object) As String
    Dim lst As Collection
    Set lst = New Collection
    Dim buf As String
    Dim i As Long
    With comp.CodeModule
        For i = 1 To .CountOfLines
            If buf <> .ProcOfLine(i, 0) Then
                buf = .ProcOfLine(i, 0)
                lst.Add "  [" + buf + "]"
            End If
        Next i
    End With
    get_fanction_names = Join( _
        mUtil.CollectionToArrayLet(lst), _
        vbCrLf _
    )
End Function
'是否为vba模块
'vbext_ct_StdModule 1 标准模块
'vbext_ct_ClassModule 2 类模块
'vbext_ct_MSForm 3 Microsoft Forms
'vbext_ct_ActiveXDesigner 11 ActiveX设计器
'vbext_ct_Document 100 文档模块
Private Function is_target_module_type( _
        ByVal module As Object) As Boolean
    Select Case module.Type
        Case 1, 2, 3
            is_target_module_type = True
        Case Else
            is_target_module_type = False
    End Select
End Function
'获取模块信息
'param: projectIdx-项目索引
'return: 项目的概要信息
Function get_module_info( _
        ByVal projectIdx As Long, _
        ByVal ModuleName As String) As String
    get_module_info = vbNullString
    Dim proj As Object
    On Error Resume Next
        Set proj = mProjectLst.item(projectIdx)
    On Error GoTo 0
    If proj Is Nothing Then Exit Function
    Dim comp As Object
    On Error Resume Next
        Set comp = proj.VBComponents(ModuleName)
    On Error GoTo 0
    If comp Is Nothing Then Exit Function
    '项目总行数
    Dim totalCharCount As Long
    totalCharCount = 0
    Dim compX As Object
    For Each compX In proj.VBComponents
        totalCharCount = totalCharCount + GetValidCharacterCount(compX)
    Next
    get_module_info = _
        "项目名称:" & proj.Name & vbCrLf & _
        "总体步数:" & totalCharCount & vbCrLf & _
        "文件路径:" & proj.fileName & vbCrLf & _
        "模块名称:" & ModuleName & "." & get_extension(comp) & vbCrLf & _
        "模块步数:" & GetValidCharacterCount(comp) & vbCrLf & _
        "函数列表:" & vbCrLf & get_fanction_names(comp)
End Function
'获取组件除去注释部分的字符数
'param: vbComp-目标组件
Private Function GetValidCharacterCount( _
        ByVal vbComp As Object) As Long
    Dim codemod As Object ' CodeModule
    Dim totalChars As Long
    Dim i As Long
    Dim codeLine As String
    ' 获取CodeModule对象
    Set codemod = vbComp.CodeModule
    totalChars = 0
    ' 检查每行并排除注释
    For i = 1 To codemod.CountOfLines
        codeLine = VBA.Trim(codemod.Lines(i, 1))
        If Left(codeLine, 1) <> "'" Then
            totalChars = totalChars + Len(codeLine)
        End If
    Next i
    ' 返回结果
    GetValidCharacterCount = totalChars
End Function
'删除项目内的vba模块并导入
'param: projectIdx-项目索引
Sub import_project( _
        ByVal projectIdx As Long)
    Dim proj As Object
    On Error Resume Next
        Set proj = mProjectLst.item(projectIdx)
    On Error GoTo 0
    If proj Is Nothing Then Exit Sub
    Dim KEY As String
    KEY = Replace(proj.fileName, "\", SEPARATOR)
    If Not mUserDict.Exists(KEY) Then Exit Sub
    Dim path As String
    path = mUserDict(KEY)("path")
    If Not mUtil.GetFso().FolderExists(path) Then Exit Sub
    Call remove_modules(projectIdx)
    Call import_modules(proj, path)
End Sub
'根据项目名获取文件夹-如果没有则创建
'param: projectIdx-项目索引
'param: parentDirPath-父文件夹路径
'return: 创建的文件夹路径
Function get_dir_by_project_name( _
        ByVal projectIdx As Long, _
        ByVal parentDirPath As String) As String
    Dim proj As Object
    On Error Resume Next
        Set proj = mProjectLst.item(projectIdx)
    On Error GoTo 0
    If proj Is Nothing Then Exit Function
    Dim path As String
    path = parentDirPath & "\" & proj.Name
    Dim fso As Object
    Set fso = mUtil.GetFso()
    If Not fso.FolderExists(path) Then
        fso.CreateFolder path
    End If
    get_dir_by_project_name = path
End Function
'导入文件夹内的文件
'param: proj-项目
'param: dirPath-导入的文件夹路径
Private Sub import_modules( _
        ByVal proj As Object, _
        ByVal dirPath As String)
    Dim fileLst As Collection
    Set fileLst = get_target_file_path_list( _
        dirPath, _
        Array( _
            "cls", _
            "frm", _
            "bas" _
        ) _
    )
    Dim path As Variant ' String
    For Each path In fileLst
        On Error Resume Next
            proj.VBComponents.import path
        On Error GoTo 0
    Next
End Sub
'获取指定路径内指定扩展名的文件
'param: path-文件夹路径
'param: targetExtensions-目标扩展名
'return: 文件路径集合
Private Function get_target_file_path_list( _
        ByVal path As String, _
        ByVal targetExtensions As Variant) As Collection
    Dim lst As Collection
    Set lst = New Collection
    Set get_target_file_path_list = lst
    Dim fso As Object
    Set fso = mUtil.GetFso()
    Dim dir As Object
    Set dir = fso.GetFolder(path)
    Dim file As Object
    Dim ext As String
    For Each file In dir.Files
        ext = fso.GetExtensionName(file.Name)
        If Not UBound(filter(targetExtensions, ext)) < 0 Then
            lst.Add file.path
        End If
    Next
End Function
'删除项目内的vba模块
'param: projectIdx-项目索引
Private Sub remove_modules( _
        ByVal projectIdx As Long)
    Dim proj As Object
    On Error Resume Next
        Set proj = mProjectLst.item(projectIdx)
    On Error GoTo 0
    If proj Is Nothing Then Exit Sub
    Dim lst As Collection
    Set lst = get_module_name_list(projectIdx)
    Dim Name As Variant ' String
    Dim comp As Object
    For Each Name In get_module_name_list(projectIdx)
        Set comp = proj.VBComponents(Name)
        proj.VBComponents.Remove comp
    Next
End Sub
'导出项目内的vba模块
'param: projectIdx-项目索引
'param: dirPath-文件夹路径
'param: isOpen(opt)-是否打开?
Sub export_project( _
        ByVal projectIdx As Long, _
        ByVal dirPath As String, _
        Optional ByVal isOpen As Boolean = True)
    Dim proj As Object
    On Error Resume Next
        Set proj = mProjectLst.item(projectIdx)
    On Error GoTo 0
    If proj Is Nothing Then Exit Sub
    
    Dim Name 'As String
    Dim comp As Object
    For Each Name In get_module_name_list(projectIdx)
        Set comp = proj.VBComponents(Name)
        On Error Resume Next
            Dim fullPath As String
            fullPath = dirPath & "\" & comp.Name & "." & get_extension(comp)
            comp.Export fullPath
            If Not Err.Number = 0 Then
                MsgBox "导出失败，请删除.git以外的文件后重试"
                Exit Sub
            End If
        On Error GoTo 0
    Next
    ' 批量转换为UTF-8，效率更高
    ConvertFolderToUtf8 dirPath
    update_userdata proj, dirPath
    If isOpen Then
        open_folder_dy_explorer dirPath
    End If
End Sub
'导出项目内的vba模块到CATVBA文件夹内
'param: projectIdx-项目索引
'param: isOpen(opt)-是否打开?
Sub export_project_child_folder( _
        ByVal projectIdx As Long, _
        Optional ByVal isOpen As Boolean = True)
    Dim proj As Object
    On Error Resume Next
        Set proj = mProjectLst.item(projectIdx)
    On Error GoTo 0
    If proj Is Nothing Then Exit Sub
    Dim fso As Object
    Set fso = mUtil.GetFso()
    Dim dirPath As String
    dirPath = fso.GetParentFolderName(proj.fileName) & "\" & SOURCE_FOLDER_NAME
    If Not fso.FolderExists(dirPath) Then
        fso.CreateFolder (dirPath)
    End If
    Call export_project(projectIdx, dirPath)
End Sub
'覆盖导出项目内的vba模块
'param: projectIdx-项目索引
Sub overwriting_project( _
        ByVal projectIdx As Long)
    Dim proj As Object
    On Error Resume Next
        Set proj = mProjectLst.item(projectIdx)
    On Error GoTo 0
    If proj Is Nothing Then Exit Sub
    Dim KEY As String
    KEY = Replace(proj.fileName, "\", SEPARATOR)
    Dim dirPath As String
    dirPath = mUserDict(KEY)("path")
    Dim fso As Object
    Set fso = mUtil.GetFso()
    '找不到的话删除就可以了吗？
    If Not fso.FolderExists(dirPath) Then Exit Sub
    Call remove_module_files(dirPath)
    Call export_project(projectIdx, dirPath)
End Sub
'仅打开项目文件夹
'param: projectIdx-项目索引
Sub open_folder( _
        ByVal projectIdx As Long)
    Dim proj As Object
    On Error Resume Next
        Set proj = mProjectLst.item(projectIdx)
    On Error GoTo 0
    If proj Is Nothing Then Exit Sub
    Dim KEY As String
    KEY = Replace(proj.fileName, "\", SEPARATOR)
    Dim dirPath As String
    dirPath = mUserDict(KEY)("path")
    Dim fso As Object
    Set fso = mUtil.GetFso()
    '找不到的话删除就可以了吗？
    If Not fso.FolderExists(dirPath) Then Exit Sub
    Call open_folder_dy_explorer(dirPath)
End Sub
'更新用户数据
'由于vba-json对"\\"的处理不好，所以替换为SEPARATOR
'param: proj-项目
'param: path-保存目录路径
Private Sub update_userdata( _
        ByVal proj As Object, _
        ByVal path As String)
    Dim KEY As String
    KEY = Replace(proj.fileName, "\", SEPARATOR)
    If mUserDict.Exists(KEY) Then
        mUserDict.Remove KEY
    End If
    Dim info As Object
    Set info = mUtil.InitDict()
    info.Add "name", proj.Name
    info.Add "path", path
    mUserDict.Add KEY, info
    Call cleanUp_userdata
End Sub
'获取导出用的扩展名
'https://learn.microsoft.com/ja-jp/office/vba/language/reference/visual-basic-add-in-model/properties-visual-basic-add-in-model
'vbext_ct_StdModule 1 标准模块
'vbext_ct_ClassModule 2 类模块
'vbext_ct_MSForm 3 Microsoft Forms
'vbext_ct_ActiveXDesigner 11 ActiveX设计器
'vbext_ct_Document 100 文档模块
Private Function get_extension( _
        ByVal module As Object) As String
    Dim extension As String
    Select Case module.Type
        Case 1 'vbext_ct_StdModule
            extension = "bas"
        Case 2 'vbext_ct_ClassModule
            extension = "cls"
        Case 3 'vbext_ct_MSForm
            extension = "frm"
        Case Else
            extension = ""
    End Select
    get_extension = extension
End Function
'删除模块文件
Private Sub remove_module_files( _
        ByVal dirPath As String)
    Dim fso As Object
    Set fso = mUtil.GetFso()
    If Not fso.FolderExists(dirPath) Then Exit Sub
    Dim Paths As Collection
    Set Paths = get_target_file_path_list( _
        dirPath, _
        Array( _
            "cls", _
            "frm", _
            "frx", _
            "bas" _
        ) _
    )
    Dim path As Variant ' String
    For Each path In Paths
        On Error Resume Next
            fso.DeleteFile path
        On Error GoTo 0
    Next
    '等待
    Call mUtil.Wait(1)
End Sub
'获取活动项目
'return: 此项目对象
Function get_this_project() As Object
    Set get_this_project = Nothing
    Dim thisProj As Object
    Dim proj As Object
    For Each proj In mVbe.vBProjects
        If proj.Name = THIS_PROJECT_NAME Then
            Set get_this_project = proj
            Exit Function
        End If
    Next
End Function
'获取活动项目文件夹路径
'return: 此项目的文件夹路径
Private Function get_this_dir_path() As String
    get_this_dir_path = mUtil.GetFso().GetParentFolderName( _
        get_this_project().fileName _
    )
End Function
'通过资源管理器打开文件夹
'param: dirPath-文件夹路径
Private Sub open_folder_dy_explorer( _
        ByVal dirPath As String)
    On Error Resume Next
        shell "C:\Windows\Explorer.exe " & dirPath, vbNormalFocus
    On Error GoTo 0
End Sub
'获取用户数据
'return: dict
Private Function get_user_data() As Object
    Dim path As String
    path = get_this_dir_path() & "\" & USER_JSON_NAME
    mUtil.Dump "userdata_path:" & path
    Dim dict As Object
    If mUtil.GetFso().FileExists(path) Then
        Set dict = load_json(path)
        dict("ver") = VERSION
    Else
        Set dict = mUtil.InitDict()
        dict.Add "ver", VERSION
    End If
    Set get_user_data = dict
End Function
'清理用户数据
Private Sub cleanUp_userdata()
    Dim fso As Object
    Set fso = mUtil.GetFso()
    Dim removeLst As Collection
    Set removeLst = New Collection
    Dim filePath As String
    Dim dirPath As String
    Dim KEY As Variant 'String
    For Each KEY In mUserDict.keys()
        If KEY = "ver" Then GoTo Continue
        filePath = Replace(KEY, SEPARATOR, "\")
        If Not fso.FileExists(filePath) Then
            removeLst.Add KEY
            GoTo Continue
        End If
        dirPath = mUserDict(KEY)("path")
        If Not fso.FolderExists(dirPath) Then
            removeLst.Add KEY
            GoTo Continue
        End If
Continue:
    Next
    For Each KEY In removeLst
        mUserDict.Remove KEY
    Next
End Sub
'项目是否曾被保存过
'param: projectIdx-项目索引
Function has_user_data( _
        ByVal projectIdx As Long) As Boolean
    has_user_data = False
    Dim proj As Object
    On Error Resume Next
        Set proj = mProjectLst.item(projectIdx)
    On Error GoTo 0
    If proj Is Nothing Then Exit Function
    has_user_data = mUserDict.Exists(Replace(proj.fileName, "\", SEPARATOR))
End Function
'写入json
'param: path-json文件路径
'param: 写入的dict
Private Sub save_json( _
        ByVal path As String, _
        ByVal dict As Object)
    Call mUtil.WriteFile( _
        path, _
        mJson.ConvertToJson(dict, 3) _
    )
End Sub
'读取json
'param: path-json文件路径
'return: dict
Private Function load_json( _
        ByVal path As String) As Object
    Set load_json = Nothing
    If Not mUtil.GetFso().FileExists(path) Then Exit Function
    Dim dict As Object
    Set dict = mJson.ParseJson(mUtil.ReadFile(path))
    Set load_json = dict
End Function

'批量将文件夹内的文件转换为UTF-8编码
Private Sub ConvertFolderToUtf8(ByVal dirPath As String)
    On Error Resume Next
    Dim wsh As Object
    Set wsh = CreateObject("WScript.Shell")
    If wsh Is Nothing Then Exit Sub
    
    Dim cmd As String
    ' 使用Shell执行PowerShell命令进行批量转换 (GB2312 -> UTF8)
    ' 效率优化：一次启动处理所有文件，避免反复创建进程
    ' 编码修正：System.Text.UTF8Encoding($false) = UTF-8 without BOM
    cmd = "powershell -NoProfile -WindowStyle Hidden -Command ""$d='" & dirPath & "'; $enc = New-Object System.Text.UTF8Encoding($false); Get-ChildItem -Path $d -Include *.bas,*.cls,*.frm -Recurse | ForEach-Object { $c = [System.IO.File]::ReadAllText($_.FullName, [System.Text.Encoding]::GetEncoding(936)); [System.IO.File]::WriteAllText($_.FullName, $c, $enc) }"""
    
    ' 0 = Hide Window, True = Wait for completion
    wsh.Run cmd, 0, True
    Set wsh = Nothing
    On Error GoTo 0
End Sub

Attribute VB_Name = "Cls_VbaUltiliseLib"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'/_/ cls_VbaUltiliseLib
'/_/ 主要处理数组、字典
Option Explicit
'Win API
Private Declare PtrSafe Sub Sleep Lib "kernel32" (ByVal ms As Long)
Private Const VER = "0.0.16"
'调试模式
Private m_DebugMode As Boolean
Private Const mdlname As String = "Cls_VbaUltiliseLib"
Private Sub Class_Initialize()
    m_DebugMode = True
End Sub
Property Get DebugMode() As Boolean
    DebugMode = m_DebugMode
End Property
Property Let DebugMode(ByVal Mode As Boolean)
    m_DebugMode = Mode
End Property
Function GetVer() As String
    GetVer = VER
End Function
'输出调试信息
'param:string
'return:
Sub Dump( _
        ByVal txt As String)
    If Not m_DebugMode Then Exit Sub
    Debug.Print txt
End Sub
'变量的输出调试
'param: v-变量
'param: Txt(opt): 头部注释
'return:
Sub DumpV( _
        ByVal X As Variant, _
        Optional ByVal txt As String = "")
    If Not m_DebugMode Then Exit Sub
    Debug.Print txt & DumpVariable(X)
End Sub
''' @param x As Variant
''' @return As String
Function DumpVariable( _
        ByVal X As Variant) As String
    On Error Resume Next
    Dim ty As String: ty = TypeName(X)
    Select Case ty
        Case "Boolean":     DumpVariable = X
        Case "Integer":     DumpVariable = X & "%"
        Case "Long":        DumpVariable = X & "&"
        #If Win64 Then
        Case "LongLong":    DumpVariable = X & "^"
        #End If
        Case "Single":      DumpVariable = X & "!"
        Case "Double":      DumpVariable = X & "#"
        Case "Currency":    DumpVariable = X & "@"
        Case "Byte":        DumpVariable = "CByte(" & X & ")"
        Case "Decimal":     DumpVariable = "CDec(" & X & ")"
        Case "Date"
            Dim D As String, t As String
            If Abs(X) >= 1 Then D = Month(X) & "/" & Day(X) & "/" & Year(X)
            If Not IsInt(X) Then t = Format(X, "h:nn:ss AM/PM")
            DumpVariable = "#" & VBA.Trim(D & " " & t) & "#"
        Case "String"
            If StrPtr(X) = 0 Then
                DumpVariable = "vbNullString"
            Else
                DumpVariable = """" & Replace(X, """", """""") & """"
            End If
        Case "Error"
            If IsMissing(X) Then
                DumpVariable = "Missing"
            Else
                DumpVariable = "CVErr(" & ReMatch(CStr(X), "\d+")(0) & ")"
            End If
        Case "ErrObject"
            DumpVariable = "Err " & X.Number
        Case "Empty", "Null", "Nothing", "Unknown"
            DumpVariable = ty
        Case Else
            If IsObject(X) Then
                Select Case ty
                    Case "Dictionary"
                        Dim keys As Variant
                        keys = X.keys()
                        Dim ar2 As Variant
                        ReDim ar2(X.count - 1)
                        Dim j As Long
                        For j = 0 To X.count - 1: ar2(j) = DumpVariable(keys(j)) & ":" & DumpVariable(X(keys(j))): Next
                        DumpVariable = "Dictionary(" & Join(ar2, ", ") & ")"
                    Case "Collection"
                        Dim ar3 As Variant
                        ReDim ar3(X.count - 1)
                        Dim k As Long
                        For k = 1 To X.count: ar3(k - 1) = DumpVariable(X.item(k)): Next
                        DumpVariable = "Collection(" & Join(ar3, ", ") & ")"
                    Case Else
                        DumpVariable = ToStr(X)
                End Select
            ElseIf IsArray(X) Then
                Dim rnk As Integer: rnk = ArrRank(X)
                If rnk = 1 Then
                    Dim lb As Long: lb = LBound(X)
                    Dim ub As Long: ub = UBound(X)
                    Dim ar As Variant
                    If ub - lb < 0 Then
                        ar = Array()
                    Else
                        Dim mx As Long: mx = 8 - 1
                        Dim xb As Long: xb = IIf(ub - lb < mx, ub, lb + mx)
                        ReDim ar(lb To xb)
                        Dim i As Long
                        For i = lb To xb: ar(i) = DumpVariable(X(i)): Next
                    End If
                    DumpVariable = "Array(" & Join(ar, ", ") & IIf(xb < ub, ", ...", "") & ")"
                Else
                    DumpVariable = Replace(ty, "()", "(" & String(rnk - 1, ",") & ")")
                End If
            Else
                Err.Raise 51
        End If
    End Select
    On Error GoTo 0
End Function
''' @param num As Variant(Of Numeric Or Date)
''' @return As Boolean
Function IsInt( _
        ByVal num As Variant) As Boolean
    If IsDate(num) Then num = CDbl(num)
    If Not IsNumeric(num) Then Err.Raise 13
    IsInt = num = Fix(num)
End Function
''' @param expr As String
''' @param ptrnFind As String
''' @param iCase As Boolean
''' @return As Variant(Of Array(Of String))
Private Function ReMatch( _
        ByVal expr As String, ByVal ptrnFind As String, _
        Optional ByVal iCase As Boolean = False) As Variant
    Dim ret As Variant: ret = Array()
    Dim regEx As Object:  Set regEx = CreateRegExp(ptrnFind, IIf(iCase, "i", ""))
    
    Dim ms As Object:     Set ms = regEx.Execute(expr)
    
    If ms.count < 1 Then: GoTo Ending
    Dim sms As Object:    Set sms = ms(0).SubMatches
    ReDim ret(sms.count)
    ret(0) = ms.item(0).Value
    Dim i As Integer
    For i = 1 To UBound(ret): ret(i) = sms.item(i - 1): Next
Ending:
    ReMatch = ret
End Function
''' @param x As Variant
''' @return As String
Private Function ToStr(ByVal X As Variant) As String
    If IsObject(X) Then
        On Error GoTo Err438
        ToStr = X.ToStr()
        On Error GoTo 0
    ElseIf IsArray(X) Then
        ToStr = TypeName(X)
    Else
        ToStr = X
    End If
    GoTo Escape
Err438:
    Dim e As ErrObject: Set e = Err
    Select Case e.Number
        Case 438: ToStr = TypeName(X): Resume Next
        Case Else: Err.Raise e.Number, e.Source, e.Description, e.HelpFile, e.HelpContext
    End Select
Escape:
End Function
''' @param arr As Variant(Of Array(Of T))
''' @return As Integer
Private Function ArrRank( _
        ByVal arr As Variant) As Integer
    If Not IsArray(arr) Then Err.Raise 13
    Dim X As Long
    Dim i As Integer: i = 0
    On Error Resume Next
    While Err.Number = 0: X = UBound(arr, IncrPre(i)): Wend
    ArrRank = i - 1
End Function
''' @param n As Variant
''' @param stepVal As Variant
''' @return As Variant
Private Function IncrPre( _
        ByRef n As Variant, _
        Optional ByVal stepVal As Variant = 1) As Variant
    n = n + stepVal: IncrPre = n
End Function
'*****系统函数*****
'获取APC
'param:
'return:Object(Of IApc)
Function GetApc() As Object
    Dim COMObjectName As String
    #If VBA7 Then
        COMObjectName = "MSAPC.Apc.7.1"
    #ElseIf VBA6 Then
        COMObjectName = "MSAPC.Apc.6.2"
    #End If
    Dim oApc As Object
    On Error Resume Next
    Set oApc = CreateObject(COMObjectName)
    On Error GoTo 0
    If oApc Is Nothing Then
        Set oApc = CreateObject("MSAPC.Apc")
    End If
    Set GetApc = oApc
End Function
'获取VBE
'param:
'return:Object(Of IApc)
Function GetVbe() As Object
    Set GetVbe = GetApc().VBE
End Function
'正在运行的vbproject的文件夹
'param:
'return:string
Function GetThisDir() As String
    Dim oApc As Object
    Set oApc = GetApc()
    Dim projFilePath As String
    projFilePath = oApc.ExecutingProject.VBProject.fileName
    GetThisDir = GetFso.GetParentFolderName(projFilePath)
End Function
'Scripting.Dictionary
'param:compareMode-Long
'return:Object(Of Dictionary)
Function InitDict( _
        Optional compareMode As Long = vbBinaryCompare) As Object
    Dim dict As Object
    Set dict = CreateObject("Scripting.Dictionary")
    dict.compareMode = compareMode
    Set InitDict = dict
End Function
'以字符数组为键，以数量为值创建字典
'param:txtArray-array(Of string)
'param:compareMode-Long
'return:Object(Of Dictionary)
Function InitDictByArrayCount( _
        ByVal txtArray As Variant, _
        Optional compareMode As Long = vbBinaryCompare) As Object
    Dim dict As Object
    Set dict = InitDict(compareMode)
    Dim KEY As Variant
    For Each KEY In txtArray
        If Not dict.Exists(KEY) Then
            dict(KEY) = dict(KEY) + 1
        Else
            Call dict.Add(KEY, 0)
        End If
    Next
    Set InitDictByArrayCount = dict
End Function
'是否为相同的字典 - 通过键和值进行比较，支持嵌套
'param:dict1-Object(Of Dictionary)
'param:dict2-Object(Of Dictionary
'return:boolean
Function IsEqualDict( _
        ByVal dict1 As Object, _
        ByVal dict2 As Object) As Boolean
    If dict1.count <> dict2.count Then
        IsEqualDict = False
        Exit Function
    End If
    Dim KEY As Variant
    For Each KEY In dict1.keys
        If Not dict2.Exists(KEY) Then
            IsEqualDict = False
            Exit Function
        End If
        If TypeName(dict1(KEY)) = "Dictionary" And TypeName(dict2(KEY)) = "Dictionary" Then
            ' 如果两个值都是字典，则递归比较它们
            If Not IsEqualDict(dict1(KEY), dict2(KEY)) Then
                IsEqualDict = False
                Exit Function
            End If
        ElseIf dict1(KEY) <> dict2(KEY) Then
            IsEqualDict = False
            Exit Function
        End If
    Next KEY
    IsEqualDict = True
End Function
'字典的深拷贝
'param:source-Object(Of Dictionary)
'return:Object(Of Dictionary)
Function DeepCopyDict( _
        ByVal Source As Variant) As Object
    Dim KEY As Variant
    Dim newDict As Object
    Dim Value As Variant
    Set newDict = CreateObject("Scripting.Dictionary")
    For Each KEY In Source.keys
        Value = Source.item(KEY)
        If TypeName(Value) = "Dictionary" Then
            Set Value = DeepCopyDict(Value)
        End If
        newDict.Add KEY, Value
    Next KEY
    Set DeepCopyDict = newDict
End Function
'*****数组函数*****
'指定大小的数组创建 - 初始值仅为let
'param:count-long
'param:value
'return:Variant(Of Array)
Function InitArray( _
        ByVal count As Long, _
        Optional ByVal Value As Variant = Empty) As Variant
    Dim ary() As Variant
    If count < 0 Then
        ary = Array()
    Else
        ReDim ary(count)
    End If
    If IsEmpty(Value) Then InitArray = ary
    Dim i As Long
    For i = 0 To UBound(ary)
        ary(i) = Value
    Next
    InitArray = ary
End Function
'创建连接的数组 - 不是连接而是创建新的数组
'param:ary1-Variant(Of Array)
'param:ary2-Variant(Of Array)
'return:Variant(Of Array)
Function JointArray( _
        ByVal ary1 As Variant, _
        ByVal Ary2 As Variant) As Variant
    Select Case True
        Case Not IsArray(ary1) And Not IsArray(Ary2)
            JointArray = Array() 'Empty
            Exit Function
        Case Not IsArray(ary1)
            JointArray = Ary2
            Exit Function
        Case Not IsArray(Ary2)
            JointArray = ary1
            Exit Function
        Case UBound(ary1) < 0 And UBound(Ary2) > -1
            JointArray = Ary2
            Exit Function
        Case UBound(ary1) > -1 And UBound(Ary2) < 0
            JointArray = ary1
            Exit Function
        Case UBound(ary1) < 0 And UBound(Ary2) < 0
            JointArray = Array() 'Empty
            Exit Function
        End Select
        Dim StCount&: StCount = UBound(ary1)
        ReDim Preserve ary1(UBound(ary1) + UBound(Ary2) + 1)
        Dim i&
        If IsObject(Ary2(0)) Then
            For i = StCount + 1 To UBound(ary1)
                Set ary1(i) = Ary2(i - StCount - 1)
            Next
        Else
            For i = StCount + 1 To UBound(ary1)
                ary1(i) = Ary2(i - StCount - 1)
            Next
        End If
        JointArray = ary1
End Function
'切片
'param:ary-Variant(Of Array)
'param:startIdx-Long
'param:endIdx-Long
'return:Variant(Of Array)
Function Slice( _
        ByVal ary As Variant, _
        ByVal startIdx As Long, _
        ByVal endIdx As Long) As Variant
    If Not IsArray(ary) Then Exit Function
    If endIdx - startIdx < 0 Then Exit Function
    If startIdx < 0 Then Exit Function
    If endIdx > UBound(ary) Then Exit Function
    Dim rngAry() As Variant
    ReDim rngAry(endIdx - startIdx)
    Dim i As Long
    For i = startIdx To endIdx
        rngAry(i - startIdx) = ary(i)
    Next
    Slice = rngAry
End Function
'数组的深拷贝
'param:ary-Variant(Of Array)
'return:Variant(Of Array)
Function DeepCopyArray( _
        ByVal ary As Variant) As Variant
    If Not IsArray(ary) Then Exit Function
    DeepCopyArray = Slice(ary, 0, UBound(ary))
End Function
'数组是否一致？
'param:ary1-Variant(Of Array)
'param:ary2-Variant(Of Array)
'return:Boolean
Function IsEqualArray( _
        ByVal ary1 As Variant, _
        ByVal Ary2 As Variant) As Boolean
    IsEqualArray = False
    If Not IsArray(ary1) Or Not IsArray(Ary2) Then Exit Function
    If Not UBound(ary1) = UBound(Ary2) Then Exit Function
    Dim i As Long
    For i = 0 To UBound(ary1)
        If Not ary1(i) = Ary2(i) Then Exit Function
    Next
    IsEqualArray = True
End Function
'集合的数组化 - let/set根据第一个元素判断
'集合内不要混合Let和Set元素!!
'param:lst-collection
'return:Variant(Of Array)
Function CollectionToArray( _
        ByVal lst As Variant) As Variant
    If lst.count < 1 Then
        CollectionToArray = Array()
        Exit Function
    End If
    If IsObject(lst.item(1)) Then
        CollectionToArray = CollectionToArraySet(lst)
    Else
        CollectionToArray = CollectionToArrayLet(lst)
    End If
End Function
'-集合的数组化-set
'param:lst-collection
'return:Variant(Of Array)
Function CollectionToArraySet( _
        ByVal lst As Variant) As Variant
    Dim lstCount As Long
    lstCount = lst.count
    If lstCount < 1 Then
        CollectionToArraySet = Array()
        Exit Function
    End If
    Dim ary() As Variant
    ReDim ary(lstCount - 1)
    Dim i As Long
    For i = 1 To lst.count
        Set ary(i - 1) = lst(i)
    Next
    CollectionToArraySet = ary
End Function
'-集合的数组化-let
'param:lst-collection
'return:Variant(Of Array)
Function CollectionToArrayLet( _
        ByVal lst As Variant) As Variant
    Dim lstCount As Long
    lstCount = lst.count
    If lstCount < 1 Then
        CollectionToArrayLet = Array()
        Exit Function
    End If
    Dim ary() As Variant
    ReDim ary(lstCount - 1)
    Dim i As Long
    For i = 1 To lst.count
        Let ary(i - 1) = lst(i)
    Next
    CollectionToArrayLet = ary
End Function
'数组的集合化
'param:Variant(Of Array)
'return:collection
Function ArrayToCollection( _
        ByVal ary As Variant) As Collection
    Dim lst As Collection
    Set lst = New Collection
    If UBound(ary) < 0 Then Exit Function
    Dim v As Variant
    For Each v In ary
        lst.Add v
    Next
    Set ArrayToCollection = lst
End Function
'数组切片
'param: arr-Variant(Of Array)
'param: StartIndex(opt)-起始索引
'param: EndIndex(opt)-结束索引
'return:- 切片后的数组
Function ArraySlice( _
        ByVal arr As Variant, _
        Optional ByVal StartIndex As Long = 0, _
        Optional ByVal EndIndex As Long = -1) As Variant
    ' EndIndex 省略时，设置为数组的最后一个索引
    If EndIndex = -1 Then
        EndIndex = UBound(arr)
    End If
    ' 错误检查
    If StartIndex < LBound(arr) Or EndIndex > UBound(arr) Or StartIndex > EndIndex Then
        ArraySlice = Array() ' 返回空数组
        Exit Function
    End If
    ' 设置结果数组的大小
    Dim Result() As Variant
    ReDim Result(0 To EndIndex - StartIndex)
    ' 数组切片
    Dim j As Long
    j = 0
    Dim i As Long
    For i = StartIndex To EndIndex
        If IsObject(arr(0)) Then
            Set Result(j) = arr(i)
        Else
            Let Result(j) = arr(i)
        End If
        j = j + 1
    Next i
    ArraySlice = Result
End Function
'************************************************************************
'*  冒泡排序
'*  param: arrTmp-值类型的数组
'*  return: 排序后的数组
'************************************************************************
Function BubbleSort( _
        ByVal arrTmp As Variant) As Variant
    Dim i As Long, j As Long
    Dim vTmp As Variant
    For i = LBound(arrTmp) To UBound(arrTmp) - 1
        For j = i + 1 To UBound(arrTmp)
            If ExtractNumericPart(arrTmp(j)) < ExtractNumericPart(arrTmp(i)) Then
                vTmp = arrTmp(i)
                arrTmp(i) = arrTmp(j)
                arrTmp(j) = vTmp
            End If
        Next j
    Next i
    BubbleSort = arrTmp
End Function
'------------------------------------------------------------------------
'-  提取数值部分
'-  param: sTxt-目标字符串
'-  return: 数值位置索引
'------------------------------------------------------------------------
Private Function ExtractNumericPart( _
        ByVal sTxt As String) As Long
    Dim sNumericPart As String
    Dim i As Long
    For i = 1 To Len(sTxt)
        If IsNumeric(Mid(sTxt, i, 1)) Then
            sNumericPart = sNumericPart & Mid(sTxt, i, 1)
        End If
    Next i
    ExtractNumericPart = CLng(sNumericPart)
End Function
'*****IO函数*****
'FileSystemObject
'return:Object(Of FileSystemObject)
Function GetFso() As Object
    Set GetFso = CreateObject("Scripting.FileSystemObject")
End Function
'路径/文件名/扩展名 分割
'param:FullPath-文件路径
'return:Variant(Of Array(Of String)) (0-Path 1-BaseName 2-Extension)
Function SplitPathName( _
        ByVal fullPath As String) As Variant
    Dim path(2) As Variant ' String
    With GetFso
        path(0) = .GetParentFolderName(fullPath)
        path(1) = .GetBaseName(fullPath)
        path(2) = .GetExtensionName(fullPath)
    End With
    SplitPathName = path
End Function
'路径/文件名/扩展名 连接
'param:Path-Variant(Of Array(Of String)) (0-Path 1-BaseName 2-Extension)
'return:文件路径
Function JointPathName( _
        ByVal path As Variant) As String
    JointPathName = ""
    If Not IsArray(path) Then Exit Function '未支持
    If Not UBound(path) = 2 Then Exit Function '未支持
    JointPathName = GetFso().BuildPath(path(0), path(1) & "." & path(2))
End Function
'获取不重复的路径
'重复时采用 (文件基本名)_(编号) 格式
'param:Path-文件路径
'return:无重复路径
Function GetUniquePath( _
        ByVal oldPath As String) As String
    Dim path() As Variant
    path = SplitPathName(oldPath)
    path(2) = "." & path(2)
    '替换文件名中不能使用的字符
    path(1) = ReplaceInvalidChars(path(1))
    Dim fso As Object
    Set fso = GetFso()
    Dim newPath As String
    newPath = path(0) + "\" + path(1)
    If Not fso.FileExists(newPath + path(2)) Then
        GetUniquePath = newPath + path(2)
        Exit Function
    End If
    Dim tempName As String
    Dim i As Long
    i = 0
    Do
        i = i + 1
        tempName = newPath + "_" + CStr(i) + path(2)
        If Not fso.FileExists(tempName) Then
            GetUniquePath = tempName
            Exit Function
        End If
    Loop
End Function
'************************************************************************
'*  将文件名中不能使用的字符替换为[_]
'*  param: sPath-文件名字符串
'*  return: 可以作为文件名使用的字符串
'************************************************************************
Function ReplaceInvalidChars( _
        ByVal sPath As String) As String
    Dim oRegex As Object
    Set oRegex = CreateObject("VBScript.RegExp")
    oRegex.Pattern = "[\/:*?""<>|]"
    oRegex.Global = True
    ReplaceInvalidChars = oRegex.Replace(sPath, "_")
End Function
'文件读取
'因为是按行读取所以需要用换行符分割
'param:path-string
'return:string
Function ReadFile( _
        ByVal path As String) As String
    ReadFile = ""
    On Error Resume Next
    With GetFso
        ReadFile = .OpenTextFile(path).ReadAll
        .Close
    End With
    On Error GoTo 0
End Function
'文件写入
'param:path-string
'param:txt-string
'param:IsAppending(opt)-追加时为True
Sub WriteFile( _
        ByVal path As String, _
        ByVal txt As String, _
        Optional ByVal IsAppending = False)
    Dim iIoMode As Integer
    iIoMode = IIf(IsAppending, 8, 2)
    With GetFso().OpenTextFile(path, iIoMode, True)
        On Error Resume Next
        .Write txt
        If Not Err.Number = 0 Then
            .Write "*** Write Errar ***"
        End If
        On Error GoTo 0
        .Close
    End With
End Sub
'睡眠
'param: dMillisecond-毫秒
Sub Wait( _
        ByVal dMillisecond As Double)
    Sleep dMillisecond
End Sub

Attribute VB_Name = "Cls_WsEvt"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private WithEvents pWb As Workbook
Attribute pWb.VB_VarHelpID = -1
Private Const mdlname As String = "Cls_WsEvt"
Public Sub Init(wbInstance)
    Set pWb = wbInstance
End Sub
Private Sub pWb_BeforeClose(Cancel As Boolean)
    ' 清除实例并释放对象
    Set gws = Nothing
    Set gwb = Nothing
     DoEvents
   Set xlAPP = Nothing
    Exit Sub
End Sub

Attribute VB_Name = "VbaModuleManegerView"
Attribute VB_Base = "0{6C571E55-7F85-4E54-AE82-FD04D972D2B9}{E5DAB4A8-C70F-419F-8C05-8348B917BE00}"
Attribute VB_GlobalNameSpace = False
Attribute VB_Creatable = False
Attribute VB_PredeclaredId = True
Attribute VB_Exposed = False
Attribute VB_TemplateDerived = False
Attribute VB_Customizable = False



Option Explicit
Private mUtil As Cls_VbaUltiliseLib
Private mModuleMgr As Cls_VbaMdlMgr

Private Const mdlname As String = "VbaModuleManegerView"
Private Sub UserForm_Initialize()
    Set mUtil = New Cls_VbaUltiliseLib
    Set mModuleMgr = New Cls_VbaMdlMgr
    Me.Caption = mModuleMgr.Title
    Call update_comboBox
End Sub
'** 事件 **
Private Sub btnExport_Click()
    Dim res As Boolean
    res = export_project
    Call update_listbox
    If res Then
        show_msg "导出完成"
    End If
End Sub
Private Sub btnimport_Click()
    Call import_project
    show_msg "导入完成" & vbCrLf & "请保存项目""
End Sub
Private Sub btnOverwrite_Click()
    Call overwriting_project
    show_msg "导出完成"
End Sub
Private Sub btnFinish_Click()
    Call finish
End Sub
Private Sub ListBox1_Change()
    Call update_info_txt
End Sub
Private Sub ComboBox1_Change()
    Call update_listbox
End Sub
Private Sub btnOpen_Click()
    '仅打开文件夹
    Call mModuleMgr.open_folder( _
        Me.ComboBox1.ListIndex + 1 _
    )
End Sub
'** 支持 **
'结束
Private Sub finish()
    Me.Hide
    Unload Me
End Sub
'模块列表的更新
Private Sub update_listbox()
    With Me.ListBox1
        .Clear
        .ListIndex = -1
    End With
    If Me.ComboBox1.ListIndex < 0 Then Exit Sub
    Dim Name As Variant
    For Each Name In mModuleMgr.get_module_name_list(Me.ComboBox1.ListIndex + 1)
        Call Me.ListBox1.AddItem(Name)
    Next
    Dim btnEnabled As Boolean
    If mModuleMgr.has_user_data(Me.ComboBox1.ListIndex + 1) Then
        btnEnabled = True
    Else
        btnEnabled = False
    End If
    With Me
        .btnOverwrite.Enabled = btnEnabled
        .btnImport.Enabled = btnEnabled
        .btnOpen.Enabled = btnEnabled
    End With
    '模块列表的更新
    If Me.ComboBox1.Value = mModuleMgr.project_name Then
        Me.btnImport.Enabled = False
    End If
End Sub
'信息文本的更新
Private Sub update_info_txt()
    If Me.ComboBox1.ListIndex < 0 Then
        Me.TextBox1.text = vbNullString
        Exit Sub
    End If
    Dim Value As String
    If Me.ListBox1.ListIndex < 0 Then
        Value = ""
    Else
        Value = Me.ListBox1.Value
    End If
    Me.TextBox1.text = mModuleMgr.get_module_info( _
        Me.ComboBox1.ListIndex + 1, _
        Value _
    )
End Sub
'ComboBox初始设置
Private Sub update_comboBox()
    Dim projects As Collection
    Set projects = mModuleMgr.get_project_name_list()
    If projects.count < 1 Then
        MsgBox "目标项目不存在""
        Call finish
        Exit Sub
    End If
    Dim i As Long
    For i = 1 To projects.count
        Call Me.ComboBox1.AddItem(projects.item(i))
    Next
    ComboBox1.ListIndex = 0
End Sub
'List中指定文字的索引获取
'param: value-搜索文字
'param: lst-搜索目标集合
'return: 对应索引
Function get_index_by_list( _
        ByVal Value As Variant, _
        ByVal lst As Collection) As Long
    Dim i As Long
    For i = 1 To lst.count
        If lst.item(i) = Value Then
            get_index_by_list = i - 1
            Exit Function
        End If
    Next
    get_index_by_list = -1
End Function
'项目的导入
Private Sub import_project()
    Dim projIdx As Long
    projIdx = Me.ComboBox1.ListIndex + 1
    Call mModuleMgr.import_project( _
        projIdx _
    )
    Call update_listbox
End Sub
'项目的导出
Private Function export_project() As Boolean
    export_project = False
    Dim projIdx As Long
    projIdx = Me.ComboBox1.ListIndex + 1
    Dim msg As String
    msg = "在CATVBA文件的文件夹内创建吗？" & vbCrLf & _
        "(是-文件夹内创建 否-对话框指定)"
    Select Case MsgBox(msg, vbYesNoCancel + vbQuestion, mModuleMgr.Title)
        Case vbYes
            '项目文件夹内
            mModuleMgr.export_project_child_folder ( _
                projIdx _
            )
        Case vbNo
            '对话框指定
            Dim dirPath As String
            dirPath = get_folder_path()
            If dirPath = vbNullString Then Exit Function
            Dim path As String
            path = mModuleMgr.get_dir_by_project_name( _
                projIdx, _
                dirPath _
            )
            Call mModuleMgr.export_project( _
                projIdx, _
                path _
            )
        Case Else
            '取消
            Exit Function
    End Select
    export_project = True
End Function
'文件夹路径获取对话框
'return: 文件夹路径
Private Function get_folder_path() As String
'    Dim dirPicker As New clsFolderPicker
'    get_folder_path = dirPicker.show_folder_picker()
    
    get_folder_path = KCL.selFdl
    
End Function
'项目的覆盖导出
Private Sub overwriting_project()
    Call mModuleMgr.overwriting_project( _
        Me.ComboBox1.ListIndex + 1 _
    )
End Sub
'消息
Private Sub show_msg( _
        ByVal msg As String)
    MsgBox msg, vbOKOnly, Me.Caption
End Sub
